# -*- coding: utf-8 -*-
from __future__ import unicode_literals
"""
***************************************************************************
*   Copyright (c) 2014 2015 2016 2017 2018 2019 2020 <mario52>            *
*                                                                         *
*   This file is a supplement to the FreeCAD CAx development system.      *
*                                                                         *
*   This program is free software; you can redistribute it and/or modify  *
*   it under the terms of the GNU Lesser General Public License (LGPL)    *
*   as published by the Free Software Foundation; either version 2 of     *
*   the License, or (at your option) any later version.                   *
*   for detail see the LICENCE text file.                                 *
**                                                                       **
*   Use at your own risk. The author assumes no liability for data loss.  *
*              It is advised to backup your data frequently.              *
*             If you do not trust the software do not use it.             *
**                                                                       **
*   This software is distributed in the hope that it will be useful,      *
*   but WITHOUT ANY WARRANTY; without even the implied warranty of        *
*   MERCHANTABILITY or FITNESS FOR A PARTICULAR PURPOSE.  See the         *
*   GNU Library General Public License for more details.                  *
*                                                                         *
*   You should have received a copy of the GNU Library General Public     *
*   License along with this macro; if not, write to the Free Software     *
*   Foundation, Inc., 59 Temple Place, Suite 330, Boston, MA  02111-1307  *
*   USA                                                                   *
***************************************************************************
*   http://www.freecadweb.org/wiki/index.php?title=Macro_FCCircularText   *
*           WARNING! All changes in this file will be lost and            *  
*                  may cause malfunction of the program                   *
***************************************************************************
"""
# FCCircularText.FCMacro    # Icon fromTheme FreeCAD
# ver 0.14-2 #00.14-4 #00.15 (rmu)#00.16 #0.16b #0.16c #0.16d #0.17 2020/09/26 #0.17b 2020/09/28#
#
##################################################################################################
#OS: Windows 10 (10.0)
#Word size of OS: 64-bit
#Word size of FreeCAD: 64-bit
#Version: 0.19.22474 (Git)
#Build type: Release
#Branch: master
#Hash: a44f8ffd427fa9b23b1f00dbf62d66cd152cd774
#Python version: 3.6.8
#Qt version: 5.12.1
#Coin version: 4.0.0a
#OCC version: 7.3.0
#Locale: French/Mars (fr_MA)
##################################################################################################
#
__Title__    = "FCCircularText"
__Author__   = "Mario52/zaphodbe"
__Version__  = "0.17b-cdc"
__Date__     = "2020/09/28" #YYYY/MMM/DD

__Comment__  = "This macro creates a text around a cylinder"
__Web__      = "https://forum.freecadweb.org/viewtopic.php?f=3&t=7384%22"
__Wiki__     = "https://wiki.freecadweb.org/Macro_FCCircularText"
__Icon__     = "/usr/lib/freecad/Mod/plugins/icons/FCCircularTextButtom.png"
__IconW__    = "C:/Users/YourUserName/AppData/Roaming/FreeCAD/Macro"
__Help__     = "start the macro and follow the instructions"
__Status__   = "stable"
__Requires__ = "freecad 0.19 and higher"
__Communication__ = "https://wiki.freecadweb.org/index.php?title=User:Mario52"
#

import PySide2
from PySide2 import (QtWidgets, QtCore, QtGui)
from PySide2.QtWidgets import (QWidget, QApplication, QSlider, QGraphicsView, QGraphicsScene, QVBoxLayout, QStyle)
from PySide2.QtGui import (QPainter, QColor, QIcon)
from PySide2.QtSvg import *

import Draft, Part, FreeCAD, math, PartGui, FreeCADGui
from math import sqrt, pi, sin, cos, asin, degrees, radians, tan
from FreeCAD import Base
import os, time, sys

import re
from operator import itemgetter #, attrgetter, methodcaller    # pour sort 

import WebGui
import matplotlib.font_manager

#### Detect version macro ########################################### #26/09/2020
def vesionSearch():
    try:
        import requests
        contentPage = requests.get("https://wiki.freecadweb.org/Macro_" + __Title__).text
        versionDetect = dateDetect = ""
        for i in contentPage.split("\n"):            # list page to line
            if "ctEven macro-version" in i:
                versionDetect = (i.split(">")[1])
            if "ctEven macro-date" in i:
                dateDetect = (i.split(">")[1])
            if (versionDetect != "") and (dateDetect != ""):
                break
        try:
            if (versionDetect == __Version__) and (dateDetect == __Date__):
                None
            else:
                msg = ("New version availlable : " + "\n" + 
                      str(versionDetect) + ":" + str(dateDetect) + "\n" + 
                      "You can install with AddonManager")
                FreeCAD.Console.PrintMessage("your actual version    : " + str(__Version__) + " : " + str(__Date__) + "\n")
                FreeCAD.Console.PrintMessage("new version availlable : " + str(versionDetect) + " : " + str(dateDetect) + "\n")
                diag = QtWidgets.QMessageBox(QtWidgets.QMessageBox.Information, 'New Version', msg)
                diag.setWindowModality(QtCore.Qt.ApplicationModal)
                diag.exec_()
        except Exception:
            None
        return versionDetect, dateDetect
    except Exception:
        FreeCAD.Console.PrintError("Not search version not connected for testing" + "\n")
##
##
global switchVersionSearch; switchVersionSearch = 0  # Search version switchable in 
                                                     # Tools/Edit parameter/BaseApp/Preferences/Macros/FCMmacros/FCCircularText
switchVersionSearch = FreeCAD.ParamGet("User parameter:BaseApp/Preferences/Macros/FCMmacros/" + __Title__).GetBool("switchVersionSearch")
if switchVersionSearch == 1:
    vesionSearch()
#### Detect version macro ###########################################

import sys,traceback
def sayexc(mess=''):
    exc_type, exc_value, exc_traceback = sys.exc_info()
    ttt=repr(traceback.format_exception(exc_type, exc_value,exc_traceback))
    lls=eval(ttt)
    l=len(lls)
    l2=lls[(l-3):]
    FreeCAD.Console.PrintError(mess + "\n" +"-->  ".join(l2))

import platform
global verPython ;  verPython = sys.version_info

global ui               ;ui = ""
global s                ;s  = ""
global points           ;points   = 0.0
global vec              ;vec      = 0

import FreeCADGui

#macroPath############################################################
global macroPath                                                     #  
param = FreeCAD.ParamGet("User parameter:BaseApp/Preferences/Macro") # macro path
macroPath  = param.GetString("MacroPath","") + "/"                   # macro path
macroPath  = macroPath.replace("\\","/")                             # convert the "\" to "/"
######################################################################  

indoorIcon = [
"60 46 9 1",
" 	c None",
".	c #6F2322",
"+	c #343433",
"@	c #CE1416",
"#	c #3E3E6E",
"$	c #5C5A58",
"%	c #5D5C85",
"&	c #7A7B99",
"*	c #8E8DA5",
"************************************************************",
"************************************************************",
"************************************************************",
"************************************************************",
"************************************************************",
"********************************++++++++++++****************",
"***************************+++++$$$$$$$$$$$$++**************",
"************************+++$$$$$$$$$$$$$$$$$$$++************",
"**********************++$$$$$$$$$$$$$$$$$$$$$$$$++**********",
"*******************+++$$$$$$$$$$$$$$$$$$$$$$$$$$$$+*********",
"******************++$$$$$$$$$$$$$++++$$$$$$$$$$$$$$+********",
"****************++$$$$$$$$$$+++++$$$$+++++$$$$$$$$$+********",
"***************+$$$$$$$$++++$$$$$$$@@@$$$$++$$$$$+++********",
"*************++$$$$$$$$+$$$$$@@@$$$@$$$$$$$$+$$$+$$+********",
"************+$$$$$$$$++$$$$$$@$$$$$@$$$$$$@@$+++$$$$+*******",
"***********+$$$$$$$$+$$@@@$$$@@@$$$@$$$$$@@@$+$$$$$$+*******",
"**********+$$$$$$$$+$$$@$$$$$@$$$$$@@@$$$@$@$+$$$$$$+*******",
"*********+$$$$$$$$+$$$$@@@$$$@@@$$$$+++++@@@$++$$$$$+*******",
"********+$$$$$$$$+$$$$$@$$$$$$$$$+++****@@*@+@@@$$$+********",
"*******+$$$$$$$$+$@@@$$@@@$$$++++************@*@@++*********",
"******+$$$$$$$$+$$@$@.$$$$$++****************@**@***********",
"******+$$$$$$$$+$$@@@$$$$++******************@@*@***********",
"*****+$$$$$$$$++$$@$@.$++********************@@@@***********",
"*****+$$$$$$$$++$$@$$@+*************************************",
"*****+$$$$$$++$$$$$$+***************************************",
"****+$$$$$$$+$$$$$++****************************************",
"****+$$$$$$$+$@@@.+*****************************************",
"****+$$$$$$$+$@$$+******************************************",
"****+$$$$$$$+$@@@+******************************************",
"****+$$$$$$$$.@$+*******************************************",
"****+$$$$$$$$.@$+*******************************************",
"****+$$$$$$$++$$+*******************************************",
"****+$$$$$$+++$$+*******************************************",
"*****+$$$++$$$+$+*******************************************",
"*****+$++$$$$$+$+*******************************************",
"******+$$$$$$$+++*******************************************",
"*******+$$$$$$$++*******************************************",
"*******+$$$$$$$+********************************************",
"********+$$$$$$+********************************************",
"********+$$$$++*********************************************",
"********++$++***********************************************",
"*********++*************************************************",
"************************************************************",
"************************************************************",
"************************************************************",
"************************************************************"]

helpIcon = [
"24 24 4 1",
" 	c None",
".	c #016AC5",
"+	c #F8F8FF",
"@	c #FFFFFF",
"........................",
".++++++++++++++++++++++.",
".++++++++++++++++++++++.",
".++..................++.",
".++..................++.",
".++......@@@@@@......++.",
".++.....@@@@@@@@.....++.",
".++.....@@@..@@@.....++.",
".++.....@@....@@.....++.",
".++.....@@....@@.....++.",
".++...........@@.....++.",
".++..........@@@.....++.",
".++.........@@@......++.",
".++........@@@.......++.",
".++........@@........++.",
".++........@@........++.",
".++..................++.",
".++........@@........++.",
".++........@@........++.",
".++..................++.",
".++..................++.",
".++++++++++++++++++++++.",
".++++++++++++++++++++++.",
"........................"]

executeIcon = [
"24 24 3 1",
" 	c None",
".	c #4E9A06",
"+	c #FFFFFF",
"                        ",
"                        ",
"                        ",
"                  .     ",
"                 .+.    ",
"                .+.+.   ",
"               .+...+.  ",
"              .+.....+. ",
"     .       .+.......+.",
"    .+.     .+.......+. ",
"   .+.+.   .+.......+.  ",
"  .+...+. .+.......+.   ",
" .+.....+.+.......+.    ",
".+.......+.......+.     ",
" .+.............+.      ",
"  .+...........+.       ",
"   .+.........+.        ",
"    .+.......+.         ",
"     .+.....+.          ",
"      .+...+.           ",
"       .+.+.            ",
"        .+.             ",
"         .              ",
"                        "]

quitIcon = [
"24 24 3 1",
" 	c None",
".	c #FFFFFF",
"+	c #CC0000",
"          ....          ",
"++++++++++....++++++++++",
"+.......++....++.......+",
"+.......++....++.......+",
"+.......++....++.......+",
"+...++++++....++++++...+",
"+...++++++....++++++...+",
"+...+++++......+++++...+",
"+...+++++......+++++...+",
"+...+++++......+++++...+",
"+...+++++......+++++...+",
"+...+++++......+++++...+",
"+...+++++......+++++...+",
"+...++++++++++++++++...+",
"+...++++++++++++++++...+",
"+...++++++++++++++++...+",
"+...++++++++++++++++...+",
"+...++++++++++++++++...+",
"+...++++++++++++++++...+",
"+...++++++++++++++++...+",
"+......................+",
"+......................+",
"+......................+",
"++++++++++++++++++++++++"]

resetIcon = [
"24 24 3 1",
" 	c None",
".	c #3465A4",
"+	c #888A85",
"                        ",
"      ........          ",
"     .++++++++.         ",
"    .++..+....+.  ..... ",
"    .+.. .+....+. .+++. ",
"    .+.   .+....+..+.+. ",
"    ...    .+....+.+.+. ",
"            .+....+..+. ",
"             .+......+. ",
"              .+.....+. ",
"               .+....+. ",
"  ......        .+...+. ",
"  .++++.         .++++. ",
"  .+...+.        ...... ",
"  .+....+.              ",
"  .+.....+.             ",
"  .+......+.            ",
"  .+..+....+.           ",
"  .+.+.+....+.    ...   ",
"  .+.+..+....+.   .+.   ",
"  .+++. .+....+. ..+.   ",
"  .....  .+....+..++.   ",
"          .++++++++.    ",
"           ........     "]

standInsideIcon = [
"16 16 9 1",
" 	c None",
".	c #010400",
"+	c #28090D",
"@	c #4C0000",
"#	c #770000",
"$	c #AE0000",
"%	c #262826",
"&	c #CB0000",
"*	c #FD0705",
"***********     ",
"***********     ",
"**  ***  **     ",
"**  *...........",
"    *...........",
"    *..  ...  ..",
"    ***  ...    ",
"    ***  ...    ",
"    ***  ...    ",
"    ***  ...    ",
"    ***  ...    ",
"   ***** ...    ",
"         ...    ",
"         ...    ",
"        .....   ",
"                "]

standOutsideIcon = [
"16 16 9 1",
" 	c None",
"*	c #010400",
"+	c #28090D",
"@	c #4C0000",
"#	c #770000",
"$	c #AE0000",
"%	c #262826",
"&	c #CB0000",
"..	c #FD0705",
"***********     ",
"***********     ",
"**  ***  **     ",
"**  *...........",
"    *...........",
"    *..  ...  ..",
"    ***  ...    ",
"    ***  ...    ",
"    ***  ...    ",
"    ***  ...    ",
"    ***  ...    ",
"   ***** ...    ",
"         ...    ",
"         ...    ",
"        .....   ",
"                "]

flatInsideIcon = [
"16 16 9 1",
" 	c None",
".	c #020400",
"+	c #2B0500",
"@	c #620502",
"#	c #770301",
"$	c #970300",
"%	c #B40100",
"&	c #E60002",
"*	c #FE0004",
"                ",
"                ",
"                ",
"                ",
"    **    .     ",
"   ***   ...    ",
"   **    ...    ",
"  ***   ..      ",
"  ***   ..      ",
"  ****&#...     ",
" *****$+.....%  ",
" **  &.+%@...@. ",
" **  ..#*&%@....",
"**** ...  *&$...",
" ***  ..   ** ..",
"               ."]

flatOutsideIcon = [
"16 16 9 1",
" 	c None",
"*	c #020400",
"+	c #2B0500",
"@	c #620502",
"#	c #770301",
"$	c #970300",
"%	c #B40100",
"&	c #E60002",
".	c #FE0004",
"                ",
"                ",
"                ",
"                ",
"    **    .     ",
"   ***   ...    ",
"   **    ...    ",
"  ***   ..      ",
"  ***   ..      ",
"  ****&#...     ",
" *****$+.....%  ",
" **  &.+%@...@. ",
" **  ..#*&%@....",
"**** ...  *&$...",
" ***  ..   ** ..",
"               ."]

romanIcon = [
"16 16 5 1",
" 	c None",
".	c #FD9806",
"+	c #FD9904",
"@	c #FD9905",
"#	c #FD9906",
"                ",
"                ",
"             @@ ",
"         @@@@@  ",
"     @@@@@  @@  ",
"  @@@@  @@  @@  ",
"@@  @@  @@   @@ ",
"@@@ @@   @@  @@ ",
" @@@@    @@  @@ ",
"  +@@    @@  @@ ",
"   #@@@   @  @@@",
"  @@ .@@  @@@@  ",
"  @#  @@@@@     ",
" +@@@@@         ",
" @@             ",
"                "]

arabicIcon = [
"16 16 5 1",
" 	c None",
".	c #F6972B",
"+	c #F6982B",
"@	c #F5972B",
"#	c #F7982B",
"                ",
"                ",
"                ",
"          ..    ",
"   ..   .....   ",
"  ...       ..  ",
"    .      ..   ",
"    .+     ..   ",
"    .+    @.    ",
"    .+   #....  ",
"    ...  ...    ",
"  ....          ",
"            ... ",
"     .......    ",
"   ...          ",
"                "]

redressIcon = [
"16 16 4 1",
" 	c None",
".	c #010400",
"+	c #000000",
"@	c #FD9905",
"                ",
"                ",
"..   ..+        ",
" .     .        ",
" .    ++  ..    ",
" .   +     .    ",
"...  ...   .    ",
"           .    ",
"   @      ...   ",
"   @            ",
"   @   @    ..+ ",
"   @  @       . ",
"   @@@       .+ ",
"   @@         . ",
"            ..+ ",
"                "]

axialIcon = [
"16 16 4 1",
" 	c None",
".	c #000000",
"+	c #010400",
"@	c #FD9905",
"                ",
"                ",
"++   ++.        ",
" +     +        ",
" +    ..     +. ",
" +   .       +. ",
"+++  +++    +   ",
"          ++    ",
"   @       +    ",
"   @            ",
"   @   @        ",
"   @  @    +   +",
"   @@@     + + +",
"   @@      .+.+.",
"                ",
"                "]

setIconTTF = [
"16 16 6 1",
" 	c None",
".	c #204A87",
"+	c None",
"@	c #729FCF",
"#	c #CC0000",
"$	c #EDD400",
".+++++++++++@@@@",
".++++++++@+@++@@",
".++#####++++@@+@",
".+++$#$$$++@+@+@",
".++++#$+++++++@+",
".++++#$#####++++",
".++++#$+$#$$$+++",
".++++#$++#$+++++",
".@++++$++#$+###+",
".@@++++++#$+#$$$",
"..@@+++++#$+#$++",
"...@@+++++$+###+",
"....@@++++++#$$$",
".....@@+++++#$++",
"......@@+++++$++",
"................"]

setIconFON = [
"16 16 6 1",
" 	c None",
".	c #204A87",
"+	c None",
"@	c #F57900",
"#	c #CC0000",
"$	c #EDD400",
".+++++++++++@@@@",
".++++++++@+@++@@",
".++###++++++@@+@",
".++#$$$++++@+@+@",
".++#$+++++++++@+",
".++###+###++++++",
".++#$$$#$#$+++++",
".++#$++#$#$+++++",
".@++$++#$#$##+#+",
".@@++++#$#$##$#$",
"..@@+++###$#$##$",
"...@@+++$$$#$##$",
"....@@+++++#$+#$",
".....@@++++#$+#$",
"......@@++++$++$",
"................"]

setIconOTF = [
"16 16 6 1",
" 	c None",
".	c #204A87",
"+	c None",
"@	c #4E9A06",
"#	c #CC0000",
"$	c #EDD400",
".+++++++++++@@@@",
".++++++++@+@++@@",
".++###++++++@@+@",
".++#$#$++++@+@+@",
".++#$#$+++++++@+",
".++#$#$###++++++",
".++#$#$+#$$+++++",
".++###$+#$++++++",
".@++$$$+#$+###++",
".@@+++++#$+#$$$+",
"..@@++++#$+#$+++",
"...@@++++$+###++",
"....@@+++++#$$$+",
".....@@++++#$+++",
"......@@++++$+++",
"................"]

setIconPOL = [
"16 16 12 1",
" 	c None",
".	c #204A87",
"+	c None",
"@	c #06989A",
"#	c #73D216",
"$	c #000000",
"%	c #75507B",
"&	c #729FCF",
"*	c #CC0000",
"=	c #F57900",
"-	c #EDD400",
";	c #4E9A06",
".+++++++++++@#$%",
".++++++++$+#++&$",
".++***++++++=@+%",
".++*-*-++++*+&+$",
".++*-*-+++++++*+",
".++***-***++++++",
".++*---*-*-+++++",
".++*-++*-*-+++++",
".$++-++*-*-*++++",
".*@++++*-*-*-+++",
"..#*+++***-*-+++",
"...;#+++---*-+++",
"....%=+++++*-+++",
".....;$++++****+",
"......@%++++----",
"................"]

def createSpace(text):    # detecte majuscule et ajoute un espace devant la lettre
    # return createSpace(TexTe) = Tex Te , if createSpace(TEXTE) = TEXTE
    if text.isupper():
        stringSpace = text
    else:
        try:
            stringSpace = text[0]
            for i in text[1:]:
                if re.search(r"[A-Z]", i): i = " " +  i
                stringSpace += i
        except Exception:
            stringSpace = text
    return stringSpace

def family(chaine):
    # return family(chaine)[1] = Family , family(chaine)[2] = typeCar (form [a, b, c ...]
    famille = typeCar = ""
    try:
        if chaine.find('-') != -1:
            famille = chaine[:chaine.find('-')]
            typeCar = chaine[chaine.find('-')+1:]
        else:
            famille = chaine
            typeCar = ""
    except Exception:
        famille = chaine
        typeCar = ""
    typeCar = str(createSpace(typeCar)).split()
    return [createSpace(famille), typeCar]

class MyLabelPatience():        # fenetre image d'attente de chargement
    global macroPath
    label = QtWidgets.QLabel()
    label.setText("<img src=" + macroPath + "FCCircularTextButtom.png><b><center>Wait please</center> \n\n<center>i search the fonts !\n\n</right></b>")
    ecran = FreeCADGui.getMainWindow().frameGeometry()
    xF = 250; yF = 250
    xW = (ecran.width()/2) - (xF/2)
    yW = (ecran.height()/2)- (yF/2)
    label.setGeometry(xW, yW, xF, yF)
    label.setStyleSheet("QLabel {background-color : #F0C300;font: 12pt; }");
    label.setWindowFlags(PySide2.QtCore.Qt.WindowFlags(PySide2.QtCore.Qt.FramelessWindowHint))        # pas de bords
    label.setWindowFlags(PySide2.QtCore.Qt.WindowStaysOnTopHint)         # PySide cette fonction met la fenetre en avant
#### matplotlib fin 1/5 #################################################################

try:
    _fromUtf8 = QtCore.QString.fromUtf8
except AttributeError:
    def _fromUtf8(s):
        return s

try:
    _encoding = QtGui.QApplication.UnicodeUTF8
    def _translate(context, text, disambig):
        return QtGui.QApplication.translate(context, text, disambig, _encoding)
except AttributeError:
    def _translate(context, text, disambig):
        return QtGui.QApplication.translate(context, text, disambig)

class Ui_MainWindow(QWidget):

    def __init__(self):
        super().__init__()

        global macroPath
        self.macroPath = macroPath

        self.userParams = "User parameter:BaseApp/Preferences/Macros/FCMmacros/" + __Title__

        self.sss = None
        self.exs = None

        self.uiUpdateEnabled = True

    #### matplotlib beginAngle 2/5 apres __init__ #################################################################
        #### matplotlib font textEdit
        self.FontTextSize  = 40
        self.fonteComp     = ""
        self.font          = QtGui.QFont()
        self.tableau       = [] #Index (), [chemin plus nom fichier (nomPathPolice), nom sans extension (nomSimple), nomSimpleExt (nomSimple + Ext)]
        self.index         = 0  #Index ()
        #### matplotlib font textEdit

        #### Config Begin matplotlib font #######################
                                               # https://en.wikipedia.org/wiki/Web_colors
        self.setColorTTF           = "blue"    # .TTF   color by "extension name" or hexa "#0000FF" 
        self.setColorFON           = "orange"  # .FON   color by "extension name" or hexa "#FFA500"
        self.setColorOTF           = "green"   # .OTF   color by "extension name" or hexa "#008000"
        self.setColorPOL           = "black"   # .OTHER color by "extension name" or hexa "#000000"
                                               #####
        self.switchModeTextList    = 1         # 0 = mode text normal (et noir) coupe le switchFontComBox
                                               # 1 = permet le switchFontComBox 1 (default)
                                               #####
        self.switchFontComBox      = 0         # 0 = (et switchModeTextList= 1) mode text (en couleur) dans liste ComboBox plus rapide (default)
                                               # 1 = (et switchModeTextList= 1) fontFamily dans liste ComboBox plus lent mais plus beau!
                                               #####
        self.setSystemFonts        = 1         # 0 = matplotlib.font_manager.findSystemFonts("C:/", "ttf") 
                                               #     fait toutes les fontes (dans tous les dossiers et sous dossiers du DD) time !!
                                               # 1 = matplotlib.font_manager.findSystemFonts(self.pathFont)
                                               #     fait toutes les fontes du repertoire (et dans tous les sous dossiers) (default)
                                               #####
        self.setTextAlignement     = 0         # 0 = AlignLeft (default)
                                               # 1 = AlignCenter
                                               # 2 = AlignRight
                                               #####
        self.switchResetToDefaults = 0         # 0 = pas de reset (non conseille) certains switch peuvent rester ouvert ou fermer inopinement !
                                               # 1 = reset (default)
                                               #####
        #### Config End matplotlib font #########################

        self.setDefaults()

    def setDefaults(self):
        if platform.system()   == "Windows" :
            self.fontName = "ARIAL"
            self.fontDir = "C:/Windows/Fonts/"
        elif platform.system() == "Linux" :
            self.fontName = "UBUNTU-M"
            self.fontDir = "/usr/share/fonts/"
        elif platform.system() == "Darwin":
            self.fontName = "Arial"
            self.fontDir = "/Library/Fonts/"
        else:
            self.fontName = "ARIAL"                     # Font Default
            self.fontDir = "/usr/share/fonts/"

        self.radius             = 10.0                  # radius
        self.text               = "FreeCAD the best "   # FreeCad The Best your text
        self.beginAngle         = 90.0                  # begin text
        self.endAngle           = -270.0                # must exceed the number of characters of text
        self.characterSize      = 2.0                   # size font

        self.helixBase          = 0.0                   # base of helix
        self.helixEnd           = 0.0                   # end of helix (heigth)
        self.helixPitch         = 2.0                   # Pas of helix
        self.helixCharPerTern   = 10                    # number char by Pas
        self.helixLoops         = 1                     # number of loops 

        self.PlacementX         = 0.0                   # Placement character axis X
        self.PlacementY         = 0.0                   # Placement characher axis Y
        self.PlacementZ         = 0.0                   # Placement characher axis Z

        self.inclinationX       = -90.0                 # inclination character axis X
        self.inclinationY       = 0.0                   # inclination character axis Y
        self.inclinationZ       = 0.0                   # inclination character axis Z

        self.radiusSupport      = self.radius           # diameter support clock
        self.nombreFaces        = 0                     # number Faces of support 0=none 1=circle 2=rectangle 3=triangle 4,5 ... polygon

        self.extrude            = 0.0                   # extrude character
        self.extrudeSupport     = 0.0                   # extrude support
        self.rotateSupport      = 0.0                   # rotation angle of the support

        self.compound           = 0                     # cree un compose des caracteres

    def searchFont(self,pathSearch,fontName=None):
        MyLabelPatience.label.show()
        FreeCADGui.updateGui()                          # rafraichi l'ecran

        ##https://matplotlib.org/_modules/matplotlib/font_manager.html

        if self.setSystemFonts:
            files_All_Fonts = matplotlib.font_manager.findSystemFonts(pathSearch)                         # fait toutes les fontes (et dans tous les sous dossiers)
        else:
            files_All_Fonts = matplotlib.font_manager.findSystemFonts(pathSearch, "ttf")  # fait toutes les fontes ? ()

        if len(files_All_Fonts) > 0:           
            self.tableau = []
            self.index = 0

            for fonte in files_All_Fonts:
                ####
                nomPathPolice = nomFichier = nomSimpleExt = nomSimple = nomExtension = nameName = ""

                nomPathPolice = fonte.replace("\\","/")     # convert the "\" to "/"
                nomFichier    = nomPathPolice.split("/")    # complet split
                nomSimpleExt  = nomFichier[-1]              # nom avec extension
                nomSimple     = nomFichier[-1][:-4]         # nom sans extension
                nomExtension  = nomSimpleExt[nomSimpleExt.rfind('.')+1:].upper() # extension

                ####
                try:
#                    nameFamily    = matplotlib.font_manager.FontProperties(fname=fonte).get_family()            ##['sans-serif']
#                    nameStyle     = matplotlib.font_manager.FontProperties(fname=fonte).get_style()              #normal
#                    nameVariant   = matplotlib.font_manager.FontProperties(fname=fonte).get_variant()            #normal
#                    nameWeight    = matplotlib.font_manager.FontProperties(fname=fonte).get_weight()             #normal
#                    nameStretch   = matplotlib.font_manager.FontProperties(fname=fonte).get_stretch()            #normal
#                    nameFileComp  = matplotlib.font_manager.FontProperties(fname=fonte).get_file()              ##c:\windows\fonts\NotoNaskhArabicUI-Regular.ttf
#                    nameSize      = matplotlib.font_manager.FontProperties(fname=fonte).get_size()               #10.0
                    nameName      = matplotlib.font_manager.FontProperties(fname=fonte).get_name()              ##Noto Naskh Arabic UI
#                    nameSizePoint = matplotlib.font_manager.FontProperties(fname=fonte).get_size_in_points()     #10.0
#                    nameSlant     = matplotlib.font_manager.FontProperties(fname=fonte).get_slant()              #normal
#                    namePattern   = matplotlib.font_manager.FontProperties(fname=fonte).get_fontconfig_pattern() #:family=sans-serif:style=normal:variant=normal:weight=normal:stretch=normal:file=c:\windows\fonts\NotoNaskhArabicUI-Regular.ttf:size=10.0
                except Exception:
                    nameFamily = nameStyle = nameVariant = nameWeight = nameStretch = nameFileComp = nameSize = nameName = nameSizePoint = nameSlant = namePattern = ""
                ####
                if nameName == "" :
                    nameName = nomSimple
                self.tableau.append([0, nomPathPolice, nomSimple, nomSimpleExt.upper(), nomExtension.upper(), nameName])
                
            self.tableau = sorted(self.tableau, key=itemgetter(3))          # sorted by nomSimple.upper()

            try:
                for line in range(len(self.tableau)):                       # enleve les doubles (bon)
                    if self.tableau[line][2] == self.tableau[line + 1][2]:  # enleve les doubles (bon)
                        del(self.tableau[line + 1])                         # enleve les doubles (bon)
            except Exception:
                None

            self.comboBoxPy.clear()
            for line in range(len(self.tableau)): 
                try:
                    self.tableau[line][0] = line                 # ajoute le numero de ligne
                    if fontName is not None and self.tableau[line][2].upper() == fontName.upper(): # detecte la fonte de base
                        self.index = line
                        self.fontPath = self.tableau[line][1]
                    ####Section common color and font begin ######################
                    model = self.comboBoxPy.model()

                    if self.switchModeTextList == 1:
                        if self.tableau[line][4] == "TTF":
                            item = QtGui.QStandardItem(QtGui.QPixmap(setIconTTF), str(line))
                            item.setForeground(QtGui.QColor(self.setColorTTF))
                        elif self.tableau[line][4] == "FON":
                            item = QtGui.QStandardItem(QtGui.QPixmap(setIconFON), str(line))
                            item.setForeground(QtGui.QColor(self.setColorFON))
                        elif self.tableau[line][4] == "OTF":
                            item = QtGui.QStandardItem(QtGui.QPixmap(setIconOTF), str(line))
                            item.setForeground(QtGui.QColor(self.setColorOTF))
                        else:
                            item = QtGui.QStandardItem(QtGui.QPixmap(setIconPOL), str(line))
                            item.setForeground(QtGui.QColor(self.setColorPOL))

                        if   self.setTextAlignement == 0:
                            item.setTextAlignment(QtCore.Qt.AlignLeft)
                        elif self.setTextAlignement == 1:
                            item.setTextAlignment(QtCore.Qt.AlignCenter)
                        elif self.setTextAlignement == 2:
                            item.setTextAlignment(QtCore.Qt.AlignRight)
                        else:
                            self.comboBoxPy.addItem(self.tableau[line][2])    
                        model.appendRow(item)
                    else:
                        self.comboBoxPy.addItem("")
                    self.comboBoxPy.setItemText(line, self.tableau[line][2])
                    ####Section item color and font end ##########################
    
                    ####Section setfont Family switchFontComBox begin#############
                    if (self.switchFontComBox == 1) and (self.switchModeTextList == 1):
                        typeCar = font = ""
                        font = QtGui.QFont()
                        #font = item.font()
        
                        typeCar   = family(self.tableau[line][2])[1]
                        font.setBold(False)
                        font.setItalic(False)
        
                        if len(typeCar) > 0:
                            for option in typeCar:
                                if option == "Bold":
                                    font.setBold(True)
                                if (option == "Italic") or (option == "It") or (option == "Slanted"):
                                    font.setItalic(True)
                                if option == "Oblique":
                                    font.setItalic(True)
                        #'Bold''Regular''Slanted''Italic''Medium''Extra''Light''Condensed''Black''It''Semibold'
                        
                        font.setFamily(self.tableau[line][5])
                        font.setPixelSize(15)
                        if self.switchModeTextList == 1:
                            item.setFont(font)
                        else:
                            self.comboBoxPy.addItem("")
                    ####Section setfont Family switchFontComBox end###############

                except Exception:
                    FreeCAD.Console.PrintMessage("Exception: searchFont()" + "\n")
                    None

            self.update_lineEdit_NameFile()
            self.comboBoxPy.setCurrentIndex(self.index)
            self.fonteComp = self.tableau[self.index][1]
            MyLabelPatience.label.close()
            #### matplotlib fin 2/5 apres __init__ #################################################################

    def setupUi(self, MainWindow):
        self.window = MainWindow

        MainWindow.setObjectName(_fromUtf8("MainWindow"))

        self.centralWidget = QtWidgets.QWidget(MainWindow)
        self.centralWidget.setObjectName(_fromUtf8("centralWidget"))
        self.GB_Main = QtWidgets.QGroupBox()

        ## Text edit area
        self.GB_Text = QtWidgets.QGroupBox()

        self.TE_Text = QtWidgets.QTextEdit()
        self.TE_Text.setMaximumHeight(74)
        self.TE_Text.textChanged.connect(self.on_TE_Changed)

        self.frame_Option = QtWidgets.QFrame()
        self.frame_Option.setFrameShape(QtWidgets.QFrame.StyledPanel)
        self.frame_Option.setFrameShadow(QtWidgets.QFrame.Plain) #Raised) Sunken

        self.PB_Reverse = QtWidgets.QPushButton()
        self.PB_Reverse.clicked.connect(self.on_PB_Reverse)

        self.CB_Split = QtWidgets.QComboBox()
        self.CB_Split.addItem(_fromUtf8("By Character"),'')
        self.CB_Split.addItem(_fromUtf8("By Word"),' ')
        self.CB_Split.addItem(_fromUtf8("By Line"),'\n')
        self.CB_Split.activated.connect(self.on_TE_Changed)

        self.PB_Help = QtWidgets.QPushButton(MainWindow)
        self.PB_Help.setIcon(QtGui.QIcon(QtGui.QPixmap(helpIcon)))      # help icone dans une variable
        self.PB_Help.clicked.connect(self.on_PB_Help_clicked)               # help

        self.lineEdit_NameFile = QtWidgets.QLineEdit()
        self.lineEdit_NameFile.setEnabled(False)

        self.comboBoxPy = QtWidgets.QComboBox()
        self.searchFont(self.fontDir)
        QtCore.QObject.connect(self.comboBoxPy, QtCore.SIGNAL("currentIndexChanged(int)"), self.on_fontComboBoxPython)

        #### Tabbed area
        self.TW_Config = QtWidgets.QTabWidget()
        self.TW_Config.currentChanged.connect(self.on_TW_Config)

        #### Configuration Tab
        ## Presets area
        self.W_Config = QtWidgets.QWidget()
        self.TW_Config.addTab(self.W_Config, "Configuration")

        self.GB_Presets = QtWidgets.QGroupBox()

        self.PB_Incl_Flat_Inside = QtWidgets.QPushButton()
        self.PB_Incl_Flat_Inside.setIcon(QtGui.QIcon(QtGui.QPixmap(flatInsideIcon)))
        self.PB_Incl_Flat_Inside.inclinations = [90.0, 0.0, 0.0]
        self.PB_Incl_Flat_Inside.clicked.connect(self.on_PB_Incl)

        self.PB_Incl_Flat_Outside = QtWidgets.QPushButton()
        self.PB_Incl_Flat_Outside.setIcon(QtGui.QIcon(QtGui.QPixmap(flatOutsideIcon)))
        self.PB_Incl_Flat_Outside.inclinations = [-90.0, 0.0, 0.0]
        self.PB_Incl_Flat_Outside.clicked.connect(self.on_PB_Incl)

        self.PB_Incl_Stand_Inside = QtWidgets.QPushButton()
        self.PB_Incl_Stand_Inside.setIcon(QtGui.QIcon(QtGui.QPixmap(standInsideIcon)))
        self.PB_Incl_Stand_Inside.inclinations = [90.0, 0.0, 90.0]
        self.PB_Incl_Stand_Inside.clicked.connect(self.on_PB_Incl)

        self.PB_Incl_Stand_Outside = QtWidgets.QPushButton()
        self.PB_Incl_Stand_Outside.setIcon(QtGui.QIcon(QtGui.QPixmap(standOutsideIcon)))
        self.PB_Incl_Stand_Outside.inclinations = [-90.0, 0.0, 90.0]
        self.PB_Incl_Stand_Outside.clicked.connect(self.on_PB_Incl)

        self.PB_ClockArabic = QtWidgets.QPushButton()
        self.PB_ClockArabic.setIcon(QtGui.QIcon(QtGui.QPixmap(arabicIcon)))
        self.PB_ClockArabic.inclinations = [90.0, 0.0, 0.0]
        self.PB_ClockArabic.clicked.connect(self.on_PB_ClockArabic)

        self.PB_ClockRoman = QtWidgets.QPushButton()
        self.PB_ClockRoman.setIcon(QtGui.QIcon(QtGui.QPixmap(romanIcon)))
        self.PB_ClockRoman.inclinations = [90.0, 0.0, 0.0]
        self.PB_ClockRoman.clicked.connect(self.on_PB_ClockRoman)

        ## Character alignment area
        self.GB_Char_Align = QtWidgets.QGroupBox()

        self.RB_Top_Left = QtWidgets.QRadioButton()
        self.RB_Top_Left.multipliers = [0.0, 1.0, 0.0]
        self.RB_Top_Left.toggled.connect(self.on_RB_Char_Align)
        self.RB_Top_Mid = QtWidgets.QRadioButton()
        self.RB_Top_Mid.multipliers = [0.5, 1.0, 0.0]
        self.RB_Top_Mid.toggled.connect(self.on_RB_Char_Align)
        self.RB_Top_Right = QtWidgets.QRadioButton()
        self.RB_Top_Right.multipliers = [1.0, 1.0, 0.0]
        self.RB_Top_Right.toggled.connect(self.on_RB_Char_Align)

        self.RB_Mid_Left = QtWidgets.QRadioButton()
        self.RB_Mid_Left.multipliers = [0.0, 0.5, 0.0]
        self.RB_Mid_Left.toggled.connect(self.on_RB_Char_Align)
        self.RB_Mid_Mid = QtWidgets.QRadioButton()
        self.RB_Mid_Mid.multipliers = [0.5, 0.5, 0.0]
        self.RB_Mid_Mid.toggled.connect(self.on_RB_Char_Align)
        self.RB_Mid_Right = QtWidgets.QRadioButton()
        self.RB_Mid_Right.multipliers = [1.0, 0.5, 0.0]
        self.RB_Mid_Right.toggled.connect(self.on_RB_Char_Align)

        self.RB_Bot_Left = QtWidgets.QRadioButton()
        self.RB_Bot_Left.multipliers = [0.0, 0.0, 0.0]
        self.RB_Bot_Left.toggled.connect(self.on_RB_Char_Align)
        self.RB_Bot_Mid = QtWidgets.QRadioButton()
        self.RB_Bot_Mid.multipliers = [0.5, 0.0, 0.0]
        self.RB_Bot_Mid.toggled.connect(self.on_RB_Char_Align)
        self.RB_Bot_Right = QtWidgets.QRadioButton()
        self.RB_Bot_Right.multipliers = [1.0, 0.0, 0.0]
        self.RB_Bot_Right.toggled.connect(self.on_RB_Char_Align)
        # Default to the center of the character
        self.RB_Mid_Mid.setChecked(True)

        self.GB_Extrude_Align = QtWidgets.QGroupBox()

        self.RB_Extrude_Front = QtWidgets.QRadioButton()
        self.RB_Extrude_Front.multiplier = 0.0
        self.RB_Extrude_Front.toggled.connect(self.on_RB_Extrude_Align)
        self.RB_Extrude_Middle = QtWidgets.QRadioButton()
        self.RB_Extrude_Middle.multiplier = 0.5
        self.RB_Extrude_Middle.toggled.connect(self.on_RB_Extrude_Align)
        self.RB_Extrude_Back = QtWidgets.QRadioButton()
        self.RB_Extrude_Back.multiplier = 1.0
        self.RB_Extrude_Back.toggled.connect(self.on_RB_Extrude_Align)
        # Default to the back/bottom of the extrusion
        self.RB_Extrude_Back.setChecked(True)

        self.DS_Radius_Circle = QtWidgets.QDoubleSpinBox()
        self.DS_Radius_Circle.setMinimum(-99999999.0)
        self.DS_Radius_Circle.setMaximum(99999999.0)
        self.DS_Radius_Circle.setValue(self.radius)
        self.DS_Radius_Circle.valueChanged.connect(self.on_DS_Radius_Circle) #connection doubleSpinBox
        self.L_Radius_Circle = QtWidgets.QLabel()

        self.DS_Size_Character = QtWidgets.QDoubleSpinBox()
        self.DS_Size_Character.setMinimum(0.0)
        self.DS_Size_Character.setMaximum(99999999.0)
        self.DS_Size_Character.setSingleStep(1.0)
        self.DS_Size_Character.setValue(self.characterSize)
        self.DS_Size_Character.valueChanged.connect(self.on_DS_Size_Character) #connection doubleSpinBox
        self.L_Size_Character = QtWidgets.QLabel()

        self.DS_Begin_Angle = QtWidgets.QDoubleSpinBox()
        self.DS_Begin_Angle.setMinimum(-99999999.0)
        self.DS_Begin_Angle.setMaximum(99999999.0)
        self.DS_Begin_Angle.setValue(self.beginAngle)
        self.DS_Begin_Angle.valueChanged.connect(self.on_DS_Begin_Angle) #connection SpinBox
        self.L_Begin_Angle = QtWidgets.QLabel()

        self.DS_End_Angle = QtWidgets.QDoubleSpinBox()
        self.DS_End_Angle.setMinimum(-99999999.0)
        self.DS_End_Angle.setMaximum(99999999.0)
        self.DS_End_Angle.setValue(self.endAngle)
        self.DS_End_Angle.valueChanged.connect(self.on_DS_End_Angle) #connection SpinBox
        self.L_End_Angle = QtWidgets.QLabel()

        self.DS_Extrude = QtWidgets.QDoubleSpinBox()
        self.DS_Extrude.setEnabled(False)
        self.DS_Extrude.setMinimum(-99999999.0)
        self.DS_Extrude.setMaximum(99999999.0)
        self.DS_Extrude.setValue(self.extrude)
        self.DS_Extrude.valueChanged.connect(self.on_DS_Extrude) #connection doubleSpinBox

        self.CB_Extrude = QtWidgets.QCheckBox()
        self.CB_Extrude.clicked.connect(self.on_CB_Extrude) #connection checkBox

        #### Options Tab
        self.W_Options = QtWidgets.QWidget()
        self.TW_Config.addTab(self.W_Options, "Options")

        self.DS_PlacementX = QtWidgets.QDoubleSpinBox()
        self.DS_PlacementX.setEnabled(False)
        self.DS_PlacementX.setSpecialValueText(_fromUtf8(""))
        self.DS_PlacementX.setMinimum(-9999999.0)
        self.DS_PlacementX.setMaximum(9999999.99)
        self.DS_PlacementX.setValue(self.PlacementX)
        self.DS_PlacementX.valueChanged.connect(self.on_DS_PlacementX) #connection doubleSpinBox

        self.DS_PlacementY = QtWidgets.QDoubleSpinBox()
        self.DS_PlacementY.setEnabled(False)
        self.DS_PlacementY.setSpecialValueText(_fromUtf8(""))
        self.DS_PlacementY.setMinimum(-9999999.0)
        self.DS_PlacementY.setMaximum(9999999.99)
        self.DS_PlacementY.setValue(self.PlacementY)
        self.DS_PlacementY.valueChanged.connect(self.on_DS_PlacementY) #connection doubleSpinBox

        self.DS_PlacementZ = QtWidgets.QDoubleSpinBox()
        self.DS_PlacementZ.setEnabled(False)
        self.DS_PlacementZ.setSpecialValueText(_fromUtf8(""))
        self.DS_PlacementZ.setMinimum(-9999999.0)
        self.DS_PlacementZ.setMaximum(9999999.99)
        self.DS_PlacementZ.setValue(self.PlacementZ)
        self.DS_PlacementZ.valueChanged.connect(self.on_DS_PlacementZ) #connection doubleSpinBox

        self.CB_Placement = QtWidgets.QCheckBox()
        self.CB_Placement.clicked.connect(self.on_CB_Placement) #connection checkBox

        self.DS_InclinationX = QtWidgets.QDoubleSpinBox()
        self.DS_InclinationX.setMinimum(-360.0)
        self.DS_InclinationX.setMaximum(360.0)
        self.DS_InclinationX.setValue(self.inclinationX)
        self.DS_InclinationX.valueChanged.connect(self.on_DS_InclinationX) #connection doubleSpinBox

        self.DS_InclinationY = QtWidgets.QDoubleSpinBox()
        self.DS_InclinationY.setMinimum(-360.0)
        self.DS_InclinationY.setMaximum(360.0)
        self.DS_InclinationY.setValue(self.inclinationY)
        self.DS_InclinationY.valueChanged.connect(self.on_DS_InclinationY) #connection doubleSpinBox

        self.DS_InclinationZ = QtWidgets.QDoubleSpinBox()
        self.DS_InclinationZ.setMinimum(-360.0)
        self.DS_InclinationZ.setMaximum(360.0)
        self.DS_InclinationZ.setValue(self.inclinationZ)
        self.DS_InclinationZ.valueChanged.connect(self.on_DS_InclinationZ) #connection doubleSpinBox

        self.L_Inclination = QtWidgets.QLabel()

        self.CB_Fixed_Angle = QtWidgets.QCheckBox()
        self.CB_Fixed_Angle.toggled.connect(self.on_CB_Fixed_Angle)

        self.CB_Solid       = QtWidgets.QCheckBox()
        self.CB_Solid.setChecked(True)

        self.CB_Points      = QtWidgets.QCheckBox()

        self.CB_Circle      = QtWidgets.QCheckBox()

        self.CB_BoundBox    = QtWidgets.QCheckBox()

        self.CB_Progression = QtWidgets.QCheckBox()

        self.CB_Live_Update = QtWidgets.QCheckBox()

        #### Support Tab
        self.W_Support = QtWidgets.QWidget()
        self.TW_Config.addTab(self.W_Support, "Support")

        self.CB_Support = QtWidgets.QCheckBox()
        self.CB_Support.toggled.connect(self.on_CB_Support)

        self.DS_Radius_Support = QtWidgets.QDoubleSpinBox()
        self.DS_Radius_Support.setMaximum(99999999.99)
        self.DS_Radius_Support.setEnabled(False)
        self.DS_Radius_Support.setValue(self.radiusSupport)
        self.DS_Radius_Support.valueChanged.connect(self.on_DS_Radius_Support) #connection doubleSpinBox
        self.L_Radius_Support = QtWidgets.QLabel()

        self.S_Number_Faces_Support = QtWidgets.QSpinBox()
        self.S_Number_Faces_Support.setMaximum(999)
        self.S_Number_Faces_Support.setEnabled(False)
        self.S_Number_Faces_Support.setValue(self.nombreFaces)
        self.S_Number_Faces_Support.valueChanged.connect(self.on_S_Number_Faces_Support) #connection SpinBox
        self.L_Number_Faces_Support = QtWidgets.QLabel()

        self.DS_Extrude_Support = QtWidgets.QDoubleSpinBox()
        self.DS_Extrude_Support.setMinimum(-99999999.0)
        self.DS_Extrude_Support.setMaximum(99999999.0)
        self.DS_Extrude_Support.setEnabled(False)
        self.DS_Extrude_Support.setValue(self.extrudeSupport)
        self.DS_Extrude_Support.valueChanged.connect(self.on_DS_Extrude_Support) #connection doubleSpinBox
        self.L_Extrude_Support = QtWidgets.QLabel()

        self.DS_Rotate_Support = QtWidgets.QDoubleSpinBox()
        self.DS_Rotate_Support.setMinimum(-360.0)
        self.DS_Rotate_Support.setMaximum(360.0)
        self.DS_Rotate_Support.setEnabled(False)
        self.DS_Rotate_Support.setValue(self.rotateSupport)
        self.DS_Rotate_Support.valueChanged.connect(self.on_DS_Rotate_Support) #connection doubleSpinBox
        self.L_Rotate_Support = QtWidgets.QLabel()

        #### Helix Tab
        self.W_Helix = QtWidgets.QWidget()
        self.TW_Config.addTab(self.W_Helix, "Helix")

        self.CB_Helix = QtWidgets.QCheckBox()
        self.CB_Helix.toggled.connect(self.on_CB_Helix)

        self.DS_Helix_Pitch = QtWidgets.QDoubleSpinBox()
        self.DS_Helix_Pitch.setMaximum(99999999.99)
        self.DS_Helix_Pitch.setValue(self.helixPitch)
        self.DS_Helix_Pitch.setEnabled(False)
        self.DS_Helix_Pitch.valueChanged.connect(self.on_DS_Helix_Pitch) #connection doubleSpinBox
        self.L_Helix_Pitch = QtWidgets.QLabel()

        self.DS_Helix_Char_Per_Turn = QtWidgets.QDoubleSpinBox()
        self.DS_Helix_Char_Per_Turn.setMaximum(99999999.0)
        self.DS_Helix_Char_Per_Turn.setValue(self.helixCharPerTern)
        self.DS_Helix_Char_Per_Turn.setEnabled(False)
        self.DS_Helix_Char_Per_Turn.valueChanged.connect(self.on_DS_Helix_Char_Per_Turn) #connection doubleSpinBox
        self.L_Helix_Char_Per_Turn = QtWidgets.QLabel()

        self.DS_Helix_Base = QtWidgets.QDoubleSpinBox()
        self.DS_Helix_Base.setMinimum(-99999999.0)
        self.DS_Helix_Base.setMaximum(99999999.0)
        self.DS_Helix_Base.setValue(self.helixBase)
        self.DS_Helix_Base.setEnabled(False)
        self.DS_Helix_Base.valueChanged.connect(self.on_DS_Helix_Base) #connection doubleSpinBox
        self.L_Helix_Base = QtWidgets.QLabel()
      
        self.DS_Helix_End = QtWidgets.QDoubleSpinBox()
        self.DS_Helix_End.setMinimum(-99999999.0)
        self.DS_Helix_End.setMaximum(99999999.0)
        self.DS_Helix_End.setValue(self.helixEnd)
        self.DS_Helix_End.setEnabled(False)
        self.DS_Helix_End.valueChanged.connect(self.on_DS_Helix_End) #connection doubleSpinBox
        self.L_Helix_End = QtWidgets.QLabel()

        self.DS_Helix_Loops = QtWidgets.QDoubleSpinBox()
        self.DS_Helix_Loops.setMinimum(0)
        self.DS_Helix_Loops.setMaximum(99999999.0)
        self.DS_Helix_Loops.setValue(self.helixLoops)
        self.DS_Helix_Loops.setEnabled(False)
        self.DS_Helix_Loops.valueChanged.connect(self.on_DS_Helix_Loops) # connection spinBox
        self.L_Helix_Loops = QtWidgets.QLabel()

        ####
        self.GB_Command = QtWidgets.QGroupBox()

        self.PB_Exit = QtWidgets.QPushButton()
        self.PB_Exit.setIcon(QtGui.QIcon(QtGui.QPixmap(quitIcon))) # quit icone dans une variable 
        #self.PB_Exit.setIconSize(QtCore.QSize(26, 26))
        self.PB_Exit.clicked.connect(self.on_PB_Exit)

        self.PB_Reset = QtWidgets.QPushButton()
        self.PB_Reset.setEnabled(True)
        self.PB_Reset.setIcon(QtGui.QIcon(QtGui.QPixmap(resetIcon)))  # reset icone dans une variable 
        self.PB_Reset.clicked.connect(self.on_PB_Reset)

        self.PB_Benchmarks = QtWidgets.QPushButton()
        self.PB_Benchmarks.setIcon(QtGui.QIcon(QtGui.QPixmap(executeIcon)))# execute icone dans une variable 
        self.PB_Benchmarks.clicked.connect(self.on_PB_Benchmarks)

        self.PB_Execute = QtWidgets.QPushButton()
        self.PB_Execute.setIcon(QtGui.QIcon(QtGui.QPixmap(executeIcon)))# execute icone dans une variable 
        self.PB_Execute.clicked.connect(self.on_PB_Execute)

        #### gridLayout begin #######################
        self.gridLayout = QtWidgets.QGridLayout(self.centralWidget)
        self.gridLayout.setContentsMargins(10, 10, 10, 10)
        ##
        self.GL_Main = QtWidgets.QGridLayout(self.GB_Main)
        self.GL_Main.setContentsMargins(10, 10, 10, 10)
        ##
        self.GL_Text = QtWidgets.QGridLayout(self.GB_Text)  # groupes .....
        self.GL_Text.setContentsMargins(10, 10, 10, 10)
        self.GL_Text.addWidget(self.TE_Text, 0, 0, 1, 1)
        ##
        self.GL_frame_Option = QtWidgets.QGridLayout(self.frame_Option)
        self.GL_frame_Option.setContentsMargins(10, 10, 10, 10)
        self.GL_frame_Option.addWidget(self.PB_Reverse, 0, 0, 1, 1)
        self.GL_frame_Option.addWidget(self.CB_Split, 1, 0, 1, 1)
        self.GL_Text.addWidget(self.frame_Option, 0, 1, 2, 1)
        ##
        self.GL_Text.addWidget(self.lineEdit_NameFile,1, 0, 1, 1)#_Font
        self.GL_Text.addWidget(self.PB_Help,2, 1, 1, 1)
        self.GL_Text.addWidget(self.comboBoxPy,2, 0, 1, 1)
        self.GL_Main.addWidget(self.GB_Text, 0, 0, 1, 1)

        #### Configuration Tab
        self.GL_Config = QtWidgets.QGridLayout(self.W_Config)
        self.GL_Config.setContentsMargins(10, 10, 10, 10)

        self.GL_Presets = QtWidgets.QGridLayout(self.GB_Presets)
        self.GL_Presets.addWidget(self.PB_Incl_Flat_Inside, 0, 0, 1, 1)
        self.GL_Presets.addWidget(self.PB_Incl_Flat_Outside, 0, 1, 1, 1)
        self.GL_Presets.addWidget(self.PB_Incl_Stand_Inside, 1, 0, 1, 1)
        self.GL_Presets.addWidget(self.PB_Incl_Stand_Outside, 1, 1, 1, 1)
        self.GL_Presets.addWidget(self.PB_ClockArabic, 2, 0, 1, 1)
        self.GL_Presets.addWidget(self.PB_ClockRoman, 2, 1, 1, 1)
        self.GL_Config.addWidget(self.GB_Presets, 0, 0, 4, 2)

        self.GL_Char_Align = QtWidgets.QGridLayout(self.GB_Char_Align)
        self.GL_Char_Align.setContentsMargins(5, 5, 5, 5)
        self.GL_Char_Align.addWidget(self.RB_Top_Left, 0, 0, 1, 1)
        self.GL_Char_Align.addWidget(self.RB_Top_Mid, 0, 1, 1, 1)
        self.GL_Char_Align.addWidget(self.RB_Top_Right, 0, 2, 1, 1)
        self.GL_Char_Align.addWidget(self.RB_Mid_Left, 1, 0, 1, 1)
        self.GL_Char_Align.addWidget(self.RB_Mid_Mid, 1, 1, 1, 1)
        self.GL_Char_Align.addWidget(self.RB_Mid_Right, 1, 2, 1, 1)
        self.GL_Char_Align.addWidget(self.RB_Bot_Left, 2, 0, 1, 1)
        self.GL_Char_Align.addWidget(self.RB_Bot_Mid, 2, 1, 1, 1)
        self.GL_Char_Align.addWidget(self.RB_Bot_Right, 2, 2, 1, 1)
        self.GL_Config.addWidget(self.GB_Char_Align, 4, 0, 3, 1)

        self.GL_Extrude_Align = QtWidgets.QGridLayout(self.GB_Extrude_Align)
        self.GL_Extrude_Align.setContentsMargins(5, 5, 5, 5)
        self.GL_Extrude_Align.addWidget(self.RB_Extrude_Front, 0, 0, 1, 1)
        self.GL_Extrude_Align.addWidget(self.RB_Extrude_Middle, 1, 0, 1, 1)
        self.GL_Extrude_Align.addWidget(self.RB_Extrude_Back, 2, 0, 1, 1)
        self.GL_Config.addWidget(self.GB_Extrude_Align, 4, 1, 3, 1)

        self.GL_Config.addWidget(self.DS_Radius_Circle, 0, 2, 1, 1)
        self.GL_Config.addWidget(self.L_Radius_Circle, 0, 3, 1, 1)

        self.GL_Config.addWidget(self.DS_Size_Character, 1, 2, 1, 1)
        self.GL_Config.addWidget(self.L_Size_Character, 1, 3, 1, 1)

        self.GL_Config.addWidget(self.DS_Begin_Angle, 2, 2, 1, 1)
        self.GL_Config.addWidget(self.L_Begin_Angle, 2, 3, 1, 1)

        self.GL_Config.addWidget(self.DS_End_Angle, 3, 2, 1, 1)
        self.GL_Config.addWidget(self.L_End_Angle, 3, 3, 1, 1)

        self.GL_Config.addWidget(self.DS_Extrude, 4, 2, 1, 1)
        self.GL_Config.addWidget(self.CB_Extrude, 4, 3, 1, 1)

        #### Options Tab
        self.GL_Options = QtWidgets.QGridLayout(self.W_Options)
        self.GL_Options.setContentsMargins(10, 10, 10, 10)

        self.GL_Options.addWidget(self.DS_PlacementX, 0, 0, 1, 1)
        self.GL_Options.addWidget(self.DS_PlacementY, 0, 1, 1, 1)
        self.GL_Options.addWidget(self.DS_PlacementZ, 0, 2, 1, 1)
        self.GL_Options.addWidget(self.CB_Placement, 0, 3, 1, 1)

        self.GL_Options.addWidget(self.DS_InclinationX, 1, 0, 1, 1)
        self.GL_Options.addWidget(self.DS_InclinationY, 1, 1, 1, 1)
        self.GL_Options.addWidget(self.DS_InclinationZ, 1, 2, 1, 1)
        self.GL_Options.addWidget(self.L_Inclination, 1, 3, 1, 1)

        self.GL_Options.addWidget(self.CB_Fixed_Angle, 3, 0, 1, 1)
        self.GL_Options.addWidget(self.CB_Solid, 3, 1, 1, 1)
        self.GL_Options.addWidget(self.CB_Live_Update, 3, 3, 1, 1)
        self.GL_Options.addWidget(self.CB_Points, 5, 0, 1, 1)
        self.GL_Options.addWidget(self.CB_Circle, 5, 1, 1, 1)
        self.GL_Options.addWidget(self.CB_BoundBox, 5, 2, 1, 1)
        self.GL_Options.addWidget(self.CB_Progression, 5, 3, 1, 1)

        #### Support Tab
        self.GL_Support = QtWidgets.QGridLayout(self.W_Support)
        self.GL_Support.setContentsMargins(10, 10, 10, 10)

        self.GL_Support.addWidget(self.CB_Support, 0, 0, 1, 1)

        self.GL_Support.addWidget(self.DS_Radius_Support, 1, 0, 1, 1)
        self.GL_Support.addWidget(self.L_Radius_Support, 1, 1, 1, 1)

        self.GL_Support.addWidget(self.S_Number_Faces_Support, 1, 2, 1, 1)
        self.GL_Support.addWidget(self.L_Number_Faces_Support, 1, 3, 1, 1)

        self.GL_Support.addWidget(self.DS_Extrude_Support, 2, 0, 1, 1)
        self.GL_Support.addWidget(self.L_Extrude_Support, 2, 1, 1, 1)

        self.GL_Support.addWidget(self.DS_Rotate_Support, 2, 2, 1, 1)
        self.GL_Support.addWidget(self.L_Rotate_Support, 2, 3, 1, 1)

        self.GL_Main.addWidget(self.TW_Config, 1, 0, 1, 1)

        #### Helix Tab
        self.GL_Helix = QtWidgets.QGridLayout(self.W_Helix)
        self.GL_Helix.setContentsMargins(10, 10, 10, 10)

        self.GL_Helix.addWidget(self.CB_Helix, 0, 0, 1, 1)

        self.GL_Helix.addWidget(self.DS_Helix_Pitch, 1, 0, 1, 1)
        self.GL_Helix.addWidget(self.L_Helix_Pitch, 1, 1, 1, 1)
        self.GL_Helix.addWidget(self.DS_Helix_Char_Per_Turn, 1, 2, 1, 1)
        self.GL_Helix.addWidget(self.L_Helix_Char_Per_Turn, 1, 3, 1, 1)
        self.GL_Helix.addWidget(self.DS_Helix_Base, 2, 0, 1, 1)
        self.GL_Helix.addWidget(self.L_Helix_Base, 2, 1, 1, 1)
        self.GL_Helix.addWidget(self.DS_Helix_End, 2, 2, 1, 1)
        self.GL_Helix.addWidget(self.L_Helix_End, 2, 3, 1, 1)
        self.GL_Helix.addWidget(self.DS_Helix_Loops, 3, 0, 1, 1)
        self.GL_Helix.addWidget(self.L_Helix_Loops, 3, 1, 1, 1)

        #### Command Options
        self.GL_Command = QtWidgets.QGridLayout(self.GB_Command)
        self.GL_Command.setContentsMargins(10, 10, 10, 10)

        self.GL_Command.addWidget(self.PB_Exit, 2, 0, 1, 1)
        self.GL_Command.addWidget(self.PB_Reset, 2, 1, 1, 1)
        self.GL_Command.addWidget(self.PB_Benchmarks, 2, 2, 1, 1)
        self.GL_Command.addWidget(self.PB_Execute, 2, 3, 1, 1)
        self.GL_Main.addWidget(self.GB_Command, 6, 0, 1, 1)
        ####
        self.gridLayout.addWidget(self.GB_Main, 0, 0, 1, 1)
        #### gridLayout end #######################

        self.load_Settings()
        MainWindow.setCentralWidget(self.centralWidget)
        self.retranslateUi(MainWindow)
        QtCore.QMetaObject.connectSlotsByName(MainWindow)

    def retranslateUi(self, MainWindow):
        MainWindow.setWindowFlags(PySide2.QtCore.Qt.WindowStaysOnTopHint)                         # PySide cette fonction met la fenetre en avant
        MainWindow.setWindowTitle(_fromUtf8(__Title__))
        MainWindow.setWindowIcon(QtGui.QIcon(_fromUtf8(self.macroPath + "FCCircularTextButtom.png")))  # change l'icone de la fenetre principale
        self.GB_Main.setTitle(_fromUtf8("Ver : " + __Version__ + " : " +  __Date__) + " (rmu)")

        ## Text edit area
        self.GB_Text.setTitle(_fromUtf8("Text to be displayed  ( "+str(len(self.text))+" characters )"))

        self.TE_Text.setHtml(_fromUtf8(self.text))
        self.TE_Text.setToolTip(_fromUtf8("Your text to be displayed"))

        self.PB_Reverse.setText(_fromUtf8("Reverse"))
        self.PB_Reverse.setToolTip(_fromUtf8("Reverse the text edited"))

        self.CB_Split.setItemText(0,_fromUtf8("By Character"))
        self.CB_Split.setItemText(1,_fromUtf8("By Word"))
        self.CB_Split.setItemText(2,_fromUtf8("By Line"))
        self.CB_Split.setToolTip(_fromUtf8("If Word is selected, the text is split at each space.\n"
                                          "If Line is selected, the text is split by lines.\n"
                                          "Otherwise each character is used.\n\n"
                                          "If in mode Path you work with a circle," + "\n"
                                          "the last character superpose de first character ! " + "\n"
                                          "you must adding one space after the last character" + "\n"
                                          "for spacing the last and the first character" + "\n\n"
                                          "You must work with the space as the character"))

        self.PB_Help.setText(_fromUtf8("Help"))

        self.lineEdit_NameFile.setToolTip(_fromUtf8("(Number index / Number Fonts) Complete path and name of Font file"))

        self.comboBoxPy.setToolTip("Choice your Font" + "\n" +
                                   "\n" +
                                   "You must modify the configuration of display" + "\n" +
                                   "Menu Edit parameter: User parameter:BaseApp/Preferences/Macros/FCMmacros/" + __Title__ + ":" + "\n" +
                                   "####" + "\n" +
                                   "switchModeTextList= 1\t# 0 = mode text normal (the switchFontComBox is enabled)" + "\n"
                                   "\t\t\t# 1 = switchFontComBox authorized (default)" + "\n"
                                   "\t\t\t#####" + "\n"
                                   "switchFontComBox  = 1\t# 0 = mode text in color .. faster" + "\n"
                                   "\t\t\t# 1 = fontFamily listed ComboBox slower but beautiful (default)" + "\n"
                                   "\t\t\t#####" + "\n"
                                   "setSystemFonts    = 1\t# 0 = matplotlib.font_manager.findSystemFonts" + "\n"
                                   "\t\t\t#   all fonts in System font" + "\n"
                                   "\t\t\t# 1 = matplotlib.font_manager.findSystemFonts(self.pathFont) (default)" + "\n"
                                   "\t\t\t# all fonts in all directory and sub directory" + "\n"
                                   "\t\t\t#####" + "\n"
                                   "setTextAlignement = 0\t# 0 = AlignLeft (default)" + "\n"
                                   "\t\t\t# 1 = AlignCenter" + "\n"
                                   "\t\t\t# 2 = AlignRight" + "\n"
                                   "\t\t\t#####" + "\n"
                                   "fontName = ""ARIAL""\t # ARIAL" + "\n"
                                   "\t\t\t#####" + "\n"
                                   "switchResetToDefaults = 0\t # 0 by default." + "\n"
                                   "If you use this option [ switchResetToDefaults = 1 ] some switch can be opened when it should not be" + "\n"
                                   "then it is advisable to do a reset after a change one option" + "\n"
                                   "####" + "\n"
                                   "Actual configuration : " + str(self.switchModeTextList) + ", " + str(self.switchFontComBox) + ", " + str(self.setSystemFonts) + ", "
                                                             + str(self.setTextAlignement) + ", " + self.fontName + ", " + str(self.switchResetToDefaults) + "\n"
                                   "####" + "\n" +
                                   "Read the info")

        #### Tabbed area

        #### Configuration Tab
        ## Presets area
        self.GB_Presets.setTitle(_fromUtf8("Presets"))

        self.PB_Incl_Flat_Inside.setText(_fromUtf8("Flat Inside"))
        self.PB_Incl_Flat_Inside.setToolTip(_fromUtf8("Text Flat on plane oriented to inside"))

        self.PB_Incl_Flat_Outside.setText(_fromUtf8("Flat Outside"))
        self.PB_Incl_Flat_Outside.setToolTip(_fromUtf8("Text Flat on plane oriented to outside"))

        self.PB_Incl_Stand_Inside.setText(_fromUtf8("Stand Inside"))
        self.PB_Incl_Stand_Inside.setToolTip(_fromUtf8("Text Standing on plane inside of line"))

        self.PB_Incl_Stand_Outside.setText(_fromUtf8("Stand Outside"))
        self.PB_Incl_Stand_Outside.setToolTip(_fromUtf8("Text Standing on plane outside of line"))

        self.PB_ClockRoman.setText(_fromUtf8("Roman Clock"))
        self.PB_ClockRoman.setToolTip(_fromUtf8("Change text to roman numerals clock"))

        self.PB_ClockArabic.setText(_fromUtf8("Arabic Clock"))
        self.PB_ClockArabic.setToolTip(_fromUtf8("Change text to arabic clock"))

        ## Character alignment area
        self.GB_Char_Align.setTitle(_fromUtf8("Character Alignment"))

        if False:
            self.RB_Top_Left.setText(_fromUtf8("TL"))
            self.RB_Top_Mid.setText(_fromUtf8("TM"))
            self.RB_Top_Right.setText(_fromUtf8("TR"))

            self.RB_Mid_Left.setText(_fromUtf8("ML"))
            self.RB_Mid_Mid.setText(_fromUtf8("MM"))
            self.RB_Mid_Right.setText(_fromUtf8("MR"))

            self.RB_Bot_Left.setText(_fromUtf8("BL"))
            self.RB_Bot_Mid.setText(_fromUtf8("BM"))
            self.RB_Bot_Right.setText(_fromUtf8("BR"))

        self.RB_Top_Left.setToolTip(_fromUtf8("Align to character Top Left"))
        self.RB_Top_Mid.setToolTip(_fromUtf8("Align to character Top Middle"))
        self.RB_Top_Right.setToolTip(_fromUtf8("Align to character Top Right"))

        self.RB_Mid_Left.setToolTip(_fromUtf8("Align to character Middle Left"))
        self.RB_Mid_Mid.setToolTip(_fromUtf8("Align to character Center"))
        self.RB_Mid_Right.setToolTip(_fromUtf8("Align to character Middle Right"))

        self.RB_Bot_Left.setToolTip(_fromUtf8("Align to character Bottom Left"))
        self.RB_Bot_Mid.setToolTip(_fromUtf8("Align to character Bottom Middle"))
        self.RB_Bot_Right.setToolTip(_fromUtf8("Align to character Bottom Right"))

        self.GB_Extrude_Align.setTitle(_fromUtf8("Extrusion Alignment"))

        self.RB_Extrude_Front.setText(_fromUtf8("Front"))
        self.RB_Extrude_Front.setToolTip(_fromUtf8("Align to extrusion front"))
        self.RB_Extrude_Middle.setText(_fromUtf8("Middle"))
        self.RB_Extrude_Middle.setToolTip(_fromUtf8("Align to extrusion middle"))
        self.RB_Extrude_Back.setText(_fromUtf8("Back"))
        self.RB_Extrude_Back.setToolTip(_fromUtf8("Align to extrusion back"))

        self.DS_Radius_Circle.setToolTip(_fromUtf8("Give the radius of circle"))
        self.DS_Radius_Circle.setSuffix(_fromUtf8(" mm"))
        self.L_Radius_Circle.setText(_fromUtf8("Radius of circle"))

        self.DS_Size_Character.setToolTip(_fromUtf8("Size of the font"))
        self.DS_Size_Character.setSuffix(_fromUtf8(" mm"))
        self.L_Size_Character.setText(_fromUtf8("Character size"))

        self.DS_Begin_Angle.setToolTip(_fromUtf8("Starting text of the circle "))
        self.DS_Begin_Angle.setSuffix(_fromUtf8(" deg"))
        self.L_Begin_Angle.setText(_fromUtf8("Starting angle"))

        self.DS_End_Angle.setToolTip(_fromUtf8("End text of the circle "))
        self.DS_End_Angle.setSuffix(_fromUtf8(" deg"))
        self.L_End_Angle.setText(_fromUtf8("Ending angle"))

        self.DS_Extrude.setSuffix(_fromUtf8(" mm"))
        self.DS_Extrude.setToolTip(_fromUtf8("Thickness of the extrude of character. If thickness = 0 then not extrude"))

        self.CB_Extrude.setText(_fromUtf8("Extrude Char."))
        self.CB_Extrude.setToolTip(_fromUtf8("Choice extrude character or not"))

        ## Options Tab
        #### Placement Items
        self.DS_PlacementX.setSuffix(_fromUtf8(" X mm"))
        self.DS_PlacementX.setToolTip(_fromUtf8("Placement direction X"))
        self.DS_PlacementY.setSuffix(_fromUtf8(" Y mm"))
        self.DS_PlacementY.setToolTip(_fromUtf8("Placement direction Y"))
        self.DS_PlacementZ.setSuffix(_fromUtf8(" Z mm"))
        self.DS_PlacementZ.setToolTip(_fromUtf8("Placement direction Z"))
        self.CB_Placement.setText(_fromUtf8("Placement"))
        self.CB_Placement.setToolTip(_fromUtf8("Placement of character in the choice"))
        #carDegrees = b' \xc2\xb0'.decode("utf-8")    #thanks wmayer	https://forum.freecadweb.org/viewtopic.php?f=13&t=36380&p=308476#p308357

        #### Inclination Items
        self.DS_InclinationX.setSuffix(_fromUtf8(" deg X"))
        self.DS_InclinationX.setToolTip(_fromUtf8("Inclination of character around axis X"))
        self.DS_InclinationY.setSuffix(_fromUtf8(" deg Y"))
        self.DS_InclinationY.setToolTip(_fromUtf8("Inclination of character around axis Y"))
        self.DS_InclinationZ.setSuffix(_fromUtf8(" deg Z"))
        self.DS_InclinationZ.setToolTip(_fromUtf8("Inclination of character around axis Z"))
        self.L_Inclination.setText(_fromUtf8("Inclination"))

        #### Command options
        self.CB_Fixed_Angle.setText(_fromUtf8("Fixed Angle"))
        self.CB_Fixed_Angle.setToolTip(_fromUtf8("Text at fixed Angle"))

        self.CB_Solid.setText(_fromUtf8("Extrude solid"))
        self.CB_Solid.setToolTip(_fromUtf8("Force extruded objects to solids"))

        self.CB_Points.setText(_fromUtf8("Points"))
        self.CB_Points.setToolTip(_fromUtf8("Create reference points"))

        self.CB_Circle.setText(_fromUtf8("Circle"))
        self.CB_Circle.setToolTip(_fromUtf8("Create reference circle"))

        self.CB_BoundBox.setText(_fromUtf8("BoundBox"))
        self.CB_BoundBox.setToolTip(_fromUtf8("Create BoundBox on character"))

        self.CB_Progression.setText(_fromUtf8("Progression"))
        self.CB_Progression.setToolTip(_fromUtf8("Visualise the character in construction"))

        self.CB_Live_Update.setText(_fromUtf8("Live Update"))
        self.CB_Live_Update.setToolTip(_fromUtf8("Changes will modify last run objects"))

        #### Support Tab/Items
        self.CB_Support.setText(_fromUtf8("Extrude Supp."))
        self.CB_Support.setToolTip(_fromUtf8("Enable extruded support"))

        self.DS_Radius_Support.setSuffix(_fromUtf8(" mm"))
        self.DS_Radius_Support.setToolTip(_fromUtf8("Radius of the support the clock (By defaut : Radius of circle)"))
        self.L_Radius_Support.setText(_fromUtf8("Radius of support"))

        self.S_Number_Faces_Support.setToolTip(_fromUtf8("Number of side of the support 0=none, 1=circle, 2=rectangle, 3=triangle, 4=square, 5=pentagon . . . . (Thickness egal extrude)"))
        self.S_Number_Faces_Support.setSuffix(_fromUtf8(" side(s)"))
        self.L_Number_Faces_Support.setText(_fromUtf8("Support number face"))

        self.DS_Extrude_Support.setToolTip(_fromUtf8("Thickness of the extrude the support." + "\n"
                                                     "If thickness = 0 then not extrude" + "\n"
                                                     "If thickness of support is bigger than character" + "\n"
                                                     "the SpinBox is colored in red" + "\n"
                                                     "if the CheckBox [Extrude Char.] is not checked" + "\n"
                                                     "the SpinBox is colored in orange for warn that the character is at the base of the support"))
        self.DS_Extrude_Support.setSuffix(_fromUtf8(" mm"))
        self.L_Extrude_Support.setText(_fromUtf8("Extrude support"))

        self.DS_Rotate_Support.setToolTip(_fromUtf8("Rotation angle of the support shape"))
        self.DS_Rotate_Support.setSuffix(_fromUtf8(" deg"))
        self.L_Rotate_Support.setText(_fromUtf8("Rotate support"))

        #### Helix Tab/Items
        self.CB_Helix.setText(_fromUtf8("Enable helix"))
        self.CB_Helix.setToolTip(_fromUtf8("Enable helix support"))

        self.DS_Helix_Pitch.setSuffix(_fromUtf8(" mm"))
        self.DS_Helix_Pitch.setToolTip(_fromUtf8("Pitch of the text along the helix (min Size Caractere)"))
        self.L_Helix_Pitch.setText(_fromUtf8("Pitch"))

        self.DS_Helix_Char_Per_Turn.setToolTip(_fromUtf8("Number of characters for one turn of helix"))
        self.L_Helix_Char_Per_Turn.setText(_fromUtf8("Char. per turn"))

        self.DS_Helix_Base.setToolTip(_fromUtf8("Base (begin) of helix (to activate Step of Helix must be zero)"))
        self.DS_Helix_Base.setSuffix(_fromUtf8(" mm"))
        self.L_Helix_Base.setText(_fromUtf8("Base"))

        self.DS_Helix_End.setToolTip(_fromUtf8("Final height of the helix (to activate Step of Helix must be zero)"))
        self.DS_Helix_End.setSuffix(_fromUtf8(" mm"))
        self.L_Helix_End.setText(_fromUtf8("End"))

        self.DS_Helix_Loops.setToolTip(_fromUtf8("Number of partial or full loops in the helix"))
        self.L_Helix_Loops.setText(_fromUtf8("Loops"))

        ####
        self.GB_Command.setTitle(_fromUtf8("Command"))

        self.PB_Exit.setText(_fromUtf8("Exit"))
        self.PB_Exit.setToolTip(_fromUtf8("Exit FCCircularText"))

        self.PB_Reset.setText(_fromUtf8("Reset"))
        self.PB_Reset.setToolTip(_fromUtf8("Reset the macro and give the number of the characters of windows Textedit"))

        self.PB_Benchmarks.setText(_fromUtf8("Run Comp"))
        self.PB_Benchmarks.setToolTip(_fromUtf8("Execute the process and one Compount of the characters is create"))

        self.PB_Execute.setText(_fromUtf8("Run"))
        self.PB_Execute.setToolTip("Execute the process") # without Compount

    def on_fontComboBoxPython(self,indeX):                                          # 0: for fontComboBoxPython
        self.index = indeX
        self.update_lineEdit_NameFile()
        self.fontFullPath = self.tableau[self.index][1]

        famille = typeCar = self.font = ""
        self.font = QtGui.QFont()
        typeCar   = family(self.tableau[self.index][2])[1]
        self.font.setBold(False)
        self.font.setItalic(False)

        if len(typeCar) > 0:
            for option in typeCar:
                if option == "Bold":
                    self.font.setBold(True)
                if (option == "Italic") or (option == "It") or (option == "Slanted"):
                    self.font.setItalic(True)
                if option == "Oblique":
                    self.font.setItalic(True)
        #'Bold''Regular''Slanted''Italic''Medium''Extra''Light''Condensed''Black''It''Semibold'#+
        
        self.font.setFamily(self.tableau[self.index][5])
        self.font.setPointSize(self.FontTextSize)
        ####
        self.fonteComp   = self.tableau[self.index][1]
        self.fontName = self.tableau[self.index][2]

        self.fontMetrics = QtGui.QFontMetrics(self.font)
#        FreeCAD.Console.PrintMessage(str(self.index) + " , " + self.tableau[self.index][1] + " , " + self.tableau[self.index][2] + " , ' " + famille + "' , ' " + typeCar + " ' \n")
    #### matplotlib fin 5/5 #################################################################

    def on_TW_Config(self,idx):
        print("on_TW_Config",idx,self.TW_Config.tabText(idx))

    def update_lineEdit_NameFile(self):
        try:
            self.lineEdit_NameFile.setText("(" + str(self.index + 1) + "/" + str(len(self.tableau)) + ") " + self.tableau[self.index][1])
        except:
            self.lineEdit_NameFile.setText("Error select another font!")

    def on_RB_Char_Align(self, value):
        if value:
            button = self.sender()
            self.charAlignMultipliers = button.multipliers

    def on_RB_Extrude_Align(self, value):
        if value:
            button = self.sender()
            self.extrudeAlignMultiplier = button.multiplier

    def on_lineEdit_NameFile(self):

        self.pathFont = self.lineEdit_NameFile.text() 
        try:
            self.pathFont  = self.pathFont.split(")") [1]
        except Exception:
            self.pathFont  = self.pathFont

        self.searchFont(self.pathFont)
        QtCore.QObject.connect(self.comboBoxPy, QtCore.SIGNAL("currentIndexChanged(int)"), self.on_fontComboBoxPython)

    def on_TE_Changed(self):        #connection textEdit
        self.text = self.TE_Text.toPlainText()

        try:
            selectedEdge = FreeCADGui.Selection.getSelectionEx()[0].SubObjects[0]
        except Exception:
            selectedEdge = ""

        if self.CB_Split.currentData() == '\n':
            self.textData = self.text.split("\n")
            self.textLabel = self.textData[0]
            self.textDataLen = len(self.textData)
            mot = "line"
        elif self.CB_Split.currentData() == ' ':
            self.textData = self.text.split(" ")
            self.textLabel = self.textData[0]
            self.textDataLen = len(self.textData)
            mot = "word"
        else:
            self.textData = self.text
            self.textLabel = self.textData[0:10]
            self.textDataLen = len(self.textData)
            mot = "character"

        if self.textDataLen != 1:
            mot += "s"

        spaces = self.text.count(" ")
        if spaces == 1:
            espace = "space"
        else:
            espace = "spaces"

        if str(selectedEdge) != "":
            self.GB_Text.setTitle("Text to be displayed  ( "+str(self.textDataLen)+ " " + mot + " ) ( " + str(spaces) + " " + espace + " ) ( Length " + str(round(selectedEdge.Length,3)) + " mm )")
        else:
            self.GB_Text.setTitle("Text to be displayed  ( "+str(self.textDataLen)+ " " + mot + " ) ( " + str(spaces) + " " + espace + " )")

    def on_PB_Reverse(self):        #connection Reverse
        data = self.textData[::-1]

        if self.CB_Split.currentData() == '\n':
            text = '\n'.join(data)
        elif self.CB_Split.currentData() == ' ':
            text = ' '.join(data)
        else:
            text = data

        self.TE_Text.setText(_fromUtf8(text))
        self.TE_Text.repaint()
        self.on_TE_Changed()

    def on_PB_Clock(self,text=None):
        if text is not None:
            self.TE_Text.setText(_fromUtf8(text))
        self.DS_Begin_Angle.setValue(60.0)
        self.DS_End_Angle.setValue(-270.0)
        self.CB_Split.setCurrentIndex(1)
        self.RB_Top_Mid.setChecked(True)
        self.RB_Extrude_Back.setChecked(True)
        self.GB_Main.repaint()
        self.on_TE_Changed()

    def on_PB_ClockArabic(self):
        self.on_PB_Clock("1 2 3 4 5 6 7 8 9 10 11 12")
        self.on_PB_Incl()

    def on_PB_ClockRoman(self):
        self.on_PB_Clock("I II III IV V VI VII VIII IX X XI XII")
        self.on_PB_Incl()

    def on_PB_Incl(self):
        button = self.sender()
        self.DS_InclinationX.setValue(button.inclinations[0])
        self.DS_InclinationY.setValue(button.inclinations[1])
        self.DS_InclinationZ.setValue(button.inclinations[2])
        self.GB_Main.repaint()

    def on_CB_Fixed_Angle(self,value):
        if value:
            self.DS_InclinationX.setValue(0.0)
            self.DS_InclinationX.repaint()

    def on_DS_Radius_Circle(self,value):
        self.radius = value  
        self.radiusSupport = value

    def on_DS_Size_Character(self,value):
        self.characterSize = value

        if self.CB_Live_Update.isChecked() and self.sss is not None:
            for ss in self.sss:
                ss.Size = value
            FreeCADGui.updateGui()

    def on_DS_Begin_Angle(self,value):
        self.beginAngle = value
        if self.uiUpdateEnabled:
            self.update_Helix_Loops()

    def on_DS_End_Angle(self,value):
        self.endAngle = value
        if self.uiUpdateEnabled:
            self.update_Helix_Loops()

    def on_DS_PlacementX(self,value):
        self.PlacementX = value

    def on_DS_PlacementY(self,value):
        self.PlacementY = value

    def on_DS_PlacementZ(self,value):
        self.PlacementZ = value

    def on_CB_Placement(self,value):              # Placement or not Placement
        self.DS_PlacementX.setEnabled(value)
        self.DS_PlacementY.setEnabled(value)
        self.DS_PlacementZ.setEnabled(value)
        if not value:
            self.PlacementX = self.PlacementY = self.PlacementZ = 0.0
            self.DS_PlacementX.setValue(self.PlacementX)
            self.DS_PlacementY.setValue(self.PlacementY)
            self.DS_PlacementZ.setValue(self.PlacementZ)

    def on_DS_Extrude(self,value):             # 
        self.extrude = value
        if self.extrude > self.extrudeSupport:
            self.DS_Extrude_Support.setStyleSheet("background-color: QPalette.Base") # origin system
            self.DS_Extrude.setStyleSheet("background-color: QPalette.Base") # origin system
            self.CB_Extrude.setStyleSheet("background-color: QPalette.Base") # origin system
        else:
            if self.extrudeSupport >= self.extrude:
                self.DS_Extrude.setStyleSheet("background-color: rgb(224, 0, 0)")
                self.DS_Extrude_Support.setStyleSheet("background-color: rgb(224, 0, 0)")

    def on_CB_Extrude(self,value):             #
        self.DS_Extrude.setEnabled(value)
        self.RB_Extrude_Front.setEnabled(value)
        self.RB_Extrude_Middle.setEnabled(value)
        self.RB_Extrude_Back.setEnabled(value)
        self.GB_Extrude_Align.setEnabled(value)
        self.CB_Solid.setEnabled(value)

        if value: 
            self.extrude = 1.0
        else:
            self.extrude = 0.0

        if (self.extrudeSupport != 0) and (self.extrudeSupport >= self.extrude):
            self.DS_Extrude.setStyleSheet("background-color: rgb(255, 165, 0)")
            self.DS_Extrude_Support.setStyleSheet("background-color: rgb(255, 165, 0)")
            self.CB_Extrude.setStyleSheet("background-color: rgb(255, 165, 0)")
        else:
            self.DS_Extrude.setStyleSheet("background-color: QPalette.Base") # origin system
            self.CB_Extrude.setStyleSheet("background-color: QPalette.Base") # origin system

        self.DS_Extrude.setValue(self.extrude)

    def on_DS_InclinationX(self,value):        # 
        self.inclinationX = value

    def on_DS_InclinationY(self,value):        # 
        self.inclinationY = value

    def on_DS_InclinationZ(self,value):        # 
        self.inclinationZ = value

    #### Helix update functions
    def on_CB_Helix(self,value):
        self.DS_Helix_Pitch.setEnabled(value)
        self.DS_Helix_Char_Per_Turn.setEnabled(value)
        self.DS_Helix_Base.setEnabled(value)
        self.DS_Helix_End.setEnabled(value)
        self.DS_Helix_Loops.setEnabled(value)

        if not value:
            self.DS_Helix_Pitch.setValue(0.0)
            self.DS_Helix_Char_Per_Turn.setValue(1.0)
            self.DS_Helix_Base.setValue(0.0)
            self.DS_Helix_End.setValue(0.0)

        self.update_Helix_Loops()
        self.update_Helix_Char_Per_Turn()

    def on_DS_Helix_Pitch(self,value):
        self.helixPitch = value
        if self.uiUpdateEnabled:
            self.update_Helix_End()

    def on_DS_Helix_Char_Per_Turn(self,value):
        self.helixCharPerTern = value

    def on_DS_Helix_Base(self,value):
        self.helixBase = value
        if self.uiUpdateEnabled:
            self.update_Helix_End()

    def on_DS_Helix_End(self,value):
        self.helixEnd = value
        if self.uiUpdateEnabled:
            self.update_Helix_Pitch()

    def on_DS_Helix_Loops(self,value):
        self.helixLoops = value
        if self.uiUpdateEnabled:
            self.update_Helix_Pitch()
            self.update_Helix_Angle()

    def update_Helix_Pitch(self):
        self.uiUpdateEnabled = False
        if self.CB_Helix.isChecked():
            helixPitch = (self.helixEnd - self.helixBase) / self.helixLoops
            self.DS_Helix_Pitch.setValue(helixPitch)
        else:
            self.DS_Helix_Pitch.setValue(0.0)
        self.DS_Helix_Pitch.repaint()
        self.uiUpdateEnabled = True

    def update_Helix_Char_Per_Turn(self):
        self.uiUpdateEnabled = False
        if self.CB_Helix.isChecked():
            chars = (self.textDataLen - 1) or 1.0
            charsPerTurn = 360.0 / (abs(self.endAngle - self.beginAngle) / chars)
            self.DS_Helix_Char_Per_Turn.setValue(charsPerTurn)
        else:
            self.DS_Helix_Char_Per_Turn.setValue(1.0)
        self.DS_Helix_Char_Per_Turn.repaint()
        self.uiUpdateEnabled = True

    def update_Helix_End(self):
        self.uiUpdateEnabled = False
        if self.CB_Helix.isChecked():
            helixEnd = self.helixBase + self.helixPitch * self.helixLoops
            self.DS_Helix_End.setValue(helixEnd)
        else:
            self.DS_Helix_End.setValue(0.0)
        self.DS_Helix_End.repaint()
        self.uiUpdateEnabled = True

    def update_Helix_Loops(self):
        self.uiUpdateEnabled = False
        loops = abs(self.endAngle - self.beginAngle) / 360.0
        self.DS_Helix_Loops.setValue(loops)
        self.DS_Helix_Loops.repaint()
        self.uiUpdateEnabled = True
        self.update_Helix_Char_Per_Turn()

    def update_Helix_Angle(self):
        self.uiUpdateEnabled = False
        if self.CB_Helix.isChecked():
            sign = (self.endAngle - self.beginAngle) / abs(self.endAngle - self.beginAngle)
            angle = self.beginAngle + sign * self.helixLoops * 360.0
            self.DS_End_Angle.setValue(angle)
            self.DS_End_Angle.repaint()
        self.uiUpdateEnabled = True
        self.update_Helix_Char_Per_Turn()

    #### Support update functions
    def on_CB_Support(self,value):
        self.DS_Radius_Support.setEnabled(value)
        self.S_Number_Faces_Support.setEnabled(value)
        self.DS_Extrude_Support.setEnabled(value)
        self.DS_Rotate_Support.setEnabled(value)

        if value:
            self.DS_Extrude_Support.setValue(-1.0)
            self.DS_Rotate_Support.setValue(0.0)
            self.DS_Radius_Support.setValue(self.DS_Radius_Circle.value())
            self.S_Number_Faces_Support.setValue(1)
        else:
            self.DS_Extrude_Support.setValue(0.0)
            self.DS_Rotate_Support.setValue(0.0)
            self.DS_Radius_Support.setValue(0.0)
            self.S_Number_Faces_Support.setValue(0)

    def on_DS_Radius_Support(self,value):
        self.radiusSupport = value

    def on_S_Number_Faces_Support(self,value): # number Faces of support 0=none 1=circle 2=rectangle 3=triangle 4,5 ... polygon
        self.nombreFaces = value
        self.DS_Extrude_Support.setEnabled(True)
        if self.nombreFaces == 0:
            self.L_Number_Faces_Support.setText(_fromUtf8("Support number face"))
            self.DS_Extrude_Support.setEnabled(False)
        elif self.nombreFaces == 1:
            self.L_Number_Faces_Support.setText(_fromUtf8("Support Circle"))
        elif self.nombreFaces == 2:
            self.L_Number_Faces_Support.setText(_fromUtf8("Support Rectangle"))
        elif self.nombreFaces == 3:
            self.L_Number_Faces_Support.setText(_fromUtf8("Support Triangle"))
        elif self.nombreFaces == 4:
            self.L_Number_Faces_Support.setText(_fromUtf8("Support Square"))
        else :
            self.L_Number_Faces_Support.setText(_fromUtf8("Support Polygone"))

    def on_DS_Extrude_Support(self,value):     #  Clock
        self.extrudeSupport = value

    def on_DS_Rotate_Support(self,value):
        self.rotateSupport = value

    def on_PB_Reset(self):
        self.setDefaults()

        self.TE_Text.setText(_fromUtf8(self.text))

        self.CB_Split.setCurrentIndex(0)

        self.DS_Size_Character.setValue(self.characterSize)
        self.DS_Radius_Circle.setValue(self.radius)

        self.DS_Begin_Angle.setValue(self.beginAngle)
        self.DS_Begin_Angle.setEnabled(True)
        self.DS_End_Angle.setValue(self.endAngle)
        self.DS_End_Angle.setEnabled(True)

        self.DS_Extrude.setValue(self.extrude)
        self.DS_Extrude.setEnabled(False)
        self.DS_Extrude.setStyleSheet("background-color: QPalette.Base") # origin system
        self.CB_Extrude.setChecked(False)
        self.CB_Extrude.setStyleSheet("background-color: QPalette.Base") # origin system

        self.CB_Placement.setChecked(False)

        self.DS_InclinationX.setValue(self.inclinationX)
        self.DS_InclinationY.setValue(self.inclinationY)
        self.DS_InclinationZ.setValue(self.inclinationZ)

        self.CB_Helix.setEnabled(False)
        self.DS_Helix_Base.setValue(self.helixBase)
        self.DS_Helix_Base.setEnabled(False)
        self.DS_Helix_End.setValue(self.helixEnd)
        self.DS_Helix_Base.setEnabled(False)
        self.DS_Helix_Pitch.setValue(self.helixPitch)
        self.DS_Helix_Char_Per_Turn.setValue(self.helixCharPerTern)

        self.CB_Support.setChecked(False)

        self.RB_Mid_Mid.setChecked(True)

        self.on_TE_Changed()

        self.window.repaint()

    def on_PB_Benchmarks(self):                # Benchmarks
      try:
        self.compound = 1
        self.on_PB_Execute()
      except:
        sayexc("Error")
       
    def on_PB_Execute(self):         # Execute
        self.sss = []
        self.exs = []
        comP     = []

        doc = FreeCAD.ActiveDocument
        if doc == None:
            doc = FreeCAD.newDocument()

        FcString = doc.addObject("App::DocumentObjectGroup","FcString_" + self.textLabel)
        if self.CB_Points.isChecked():
            FcStringPoints = doc.addObject("App::DocumentObjectGroup","FcStringPoints_" + self.textLabel)

#### Path

        # create text on wire, arc, circle edge... 
        #
        try:
            ssel = FreeCADGui.Selection.getSelectionEx()
            selectedEdge = FreeCADGui.Selection.getSelectionEx()[0].SubObjects[0]  # select one element
            if (hasattr(selectedEdge,'Surface')) or (hasattr(selectedEdge,'Point')):
                ssel = []
        except Exception:
            ssel = []
            selectedEdge = None

        points = []
        rots = []
        if len(ssel):
            #### Calculate points along selected line
            posMultiplier = 10
            numberOfPoints = ((self.textDataLen - 1) * posMultiplier) + 1

            try:
                points = selectedEdge.discretize(numberOfPoints)    # discretize the element
            except Exception:
                FreeCAD.Console.PrintError(str("Discretize Error or selection error")+"\n")
                return

            for position in range(self.textDataLen):
                rotX = self.inclinationX - 90.0
                rotY = self.inclinationY
                rotZ = self.inclinationZ
                if not self.CB_Fixed_Angle.isChecked():
                    idx = (position * posMultiplier) or 1
                    vect = points[idx].sub(points[idx - 1])
                    rot = FreeCAD.Rotation(FreeCAD.Vector(1,0,0),vect).toEuler()

                    rotX += rot[0]
                    rotY += rot[1]
                    rotZ += rot[2]

                rots.append([rotX, rotY, rotZ])

        else:
            #### Calculate points around a circle/helix
            posMultiplier = 1
            vecligne=[FreeCAD.Vector(self.PlacementX,self.PlacementY,self.PlacementZ),FreeCAD.Vector(self.radius,0.0,0.0)]      # 
            ligne = Draft.makeWire(vecligne,closed=False,face=False,support=None)     # creation de la ligne de base
            lineName = ligne.Name

            if self.textDataLen > 1:
                angleInc = (self.endAngle - self.beginAngle)/(self.textDataLen - 1)
                zInc = (self.helixEnd - self.helixBase)/(self.textDataLen - 1)
            else:
                angleInc = 0
                zInc = 0

            angleTr = self.beginAngle
            for position in range(self.textDataLen):
                ligne.Placement = FreeCAD.Placement(FreeCAD.Vector(self.PlacementX,self.PlacementY,self.PlacementZ + self.helixBase + position * zInc), FreeCAD.Rotation(FreeCAD.Vector(0,0,1),angleTr), FreeCAD.Vector(0,0,0))
                points.append(ligne.End)
                rotX = self.inclinationX - 180.0
                rotY = self.inclinationY
                rotZ = self.inclinationZ
                if not self.CB_Fixed_Angle.isChecked():
                    rotX += angleTr

                rots.append([rotX, rotY, rotZ])

                angleTr += angleInc

            FreeCAD.ActiveDocument.removeObject(lineName)     # remove ligne de base directrice

        #### Create and place the strings
        for position in range(self.textDataLen):
            coorX, coorY, coorZ = points[position * posMultiplier]
            rotX, rotY, rotZ = rots[position]

            string = self.textData[position]
            if string == ' ':
                continue
            ss=Draft.makeShapeString(String=string,FontFile=self.fontFullPath,Size=self.characterSize,Tracking=0)
            ss.Label = string
            Draft.autogroup(ss)

            lengthX  = ss.Shape.BoundBox.XLength
            lengthY  = self.characterSize / self.fontMetrics.height() * self.fontMetrics.ascent()
            lengthZ  = ss.Shape.BoundBox.ZLength
            centreX  = lengthX * self.charAlignMultipliers[0]
            centreY  = lengthY * self.charAlignMultipliers[1]
            centreZ  = lengthZ * self.charAlignMultipliers[2]
            coorX    -= centreX
            coorY    -= centreY
            coorZ    -= centreZ

            plm = FreeCAD.Placement(FreeCAD.Vector(coorX,coorY,coorZ), FreeCAD.Rotation(rotX,rotY,rotZ), FreeCAD.Vector(centreX,centreY,centreZ)) # pitch,roll...1

            ####
            if self.extrude != 0:         # extrusion characrters
                extrudeUp = self.extrude * self.extrudeAlignMultiplier
                extrudeDn = self.extrude - extrudeUp

                CharExtrude = Draft.extrude(ss,Base.Vector(0,0,self.extrude))
                CharExtrude.LengthFwd = extrudeUp
                CharExtrude.LengthRev = extrudeDn
                CharExtrude.Label = string
                CharExtrude.Placement = plm
                CharExtrude.Solid = self.CB_Solid.isChecked()

                try:
                    CharExtrude.ViewObject.DisplayMode = u"Flat Lines"
                except Exception:
                    None

                if self.CB_BoundBox.isChecked():
                    CharExtrude.ViewObject.BoundingBox = True

                FreeCAD.ActiveDocument.getObject(CharExtrude.Name).recompute()

                comP.append(CharExtrude.Shape)
                FcString.addObject(CharExtrude)  # contener extrude
                self.exs.append(CharExtrude)
            else:
                ss.Placement=plm
                ss.Support=None
                try:
                    ss.ViewObject.DisplayMode = u"Flat Lines"
                except Exception:
                    None

                if self.CB_BoundBox.isChecked():
                    ss.ViewObject.BoundingBox = True

                comP.append(ss.Shape)
                FcString.addObject(ss)  # contener character
                self.sss.append(ss)
            ####
            if self.CB_Points.isChecked():
                pointRepere = Draft.makePoint(plm.Base)
                pointRepere.ViewObject.PointColor = (1.0,0.0,0.0)
                pointRepere.Label = string
                FreeCAD.ActiveDocument.getObject(pointRepere.Name).recompute()
                FcStringPoints.addObject(pointRepere)
            ####
            if self.CB_Progression.isChecked():
                FreeCADGui.updateGui()                                 # rafraichi l'ecran
            ####

        #### Add reference circle
        if self.CB_Circle.isChecked() and not len(ssel):
            plm = FreeCAD.Placement(FreeCAD.Vector(self.PlacementX,self.PlacementY,self.PlacementZ), FreeCAD.Rotation(FreeCAD.Vector(0,0,1),0), FreeCAD.Vector(0,0,0))
            circle = Draft.makeCircle(radius=self.radius, placement=plm, face=False, support=None)
            circle.Label = self.textLabel
            circle.ViewObject.LineColor = (1.0,0.,0.0)
            Draft.autogroup(circle)

        #### Create compound
        if self.compound == 1:                            # create compount
            comp = Part.makeCompound(comP)
            Part.show(comp)

        #### Extrude support
        if self.nombreFaces > 0:                           # support clock
            plm = FreeCAD.Placement()
            plm.Base = FreeCAD.Vector(0.0,0.0,0.0)
            plm.Rotation = FreeCAD.Rotation(self.rotateSupport,0,0)
            if self.nombreFaces == 1:                      # circle
                supp = Draft.makeCircle(self.radiusSupport,placement=plm,face=True,support=None)
            if self.nombreFaces == 2:                      # rectangle
                radiusSupport = self.radiusSupport * 2
                #plm.Base = FreeCAD.Vector(-radiusSupport, (-radiusSupport / 2), 0.0)
                supp = Draft.makeRectangle((radiusSupport * 2), radiusSupport, placement=plm, face = True)
            if self.nombreFaces > 2:                       # polygone with number faces
                supp = Draft.makePolygon(self.nombreFaces,self.radiusSupport,inscribed = False,placement = plm,face = True,support=None)

            supp.MakeFace = True
            FreeCAD.activeDocument().recompute()
            FcString.addObject(supp)                  # contener support

            if self.extrudeSupport != 0:                        # extrude support clock
                suppExtrude = Draft.extrude(supp,Base.Vector(0,0,self.extrudeSupport))
                suppExtrude.Placement = plm
                suppExtrude.Solid = self.CB_Solid.isChecked()

                FreeCAD.ActiveDocument.getObject(suppExtrude.Name).recompute()
                try:
                    suppExtrude.ViewObject.DisplayMode = u"Flat Lines"
                    if self.CB_BoundBox.isChecked():
                        suppExtrude.ViewObject.BoundingBox = True
                except Exception:
                    None

                FcString.addObject(suppExtrude)       # contener support extrude

        FreeCAD.activeDocument().recompute()

        ####Info################################################
        FreeCAD.Console.PrintMessage("______________" +"\n")
        FreeCAD.Console.PrintMessage( self.fontFullPath + "\n")
        FreeCAD.Console.PrintMessage("text          : " + str(self.text)+"\n")
        FreeCAD.Console.PrintMessage("radius        : " + str(self.radius)+"\n")
        FreeCAD.Console.PrintMessage("characterSize : " + str(self.characterSize)+"\n")
        FreeCAD.Console.PrintMessage("rotation      : " + str(self.beginAngle) + " / " + str(self.endAngle)+"\n")
        #FreeCAD.Console.PrintMessage("standing      : " + str(self.standing)+"\n")
        FreeCAD.Console.PrintMessage("_______________" +"\n")

        ####Reset################################################
        if self.switchResetToDefaults:
            self.on_PB_Reset()

    def on_PB_Help_clicked(self):
        WebGui.openBrowser("https://wiki.freecadweb.org/Macro_FCCircularText")
        FreeCAD.Console.PrintMessage("https://wiki.freecadweb.org/Macro_FCCircularText" + "\n")

    def on_PB_Exit(self):                      # Exit
        global s

        FreeCADGui.Selection.removeObserver(s)                              # desinstalle la fonction residente
        self.save_Settings()
        FreeCAD.Console.PrintMessage("Fin FCCircularText"+"\n")
        self.window.hide()

    def save_Settings(self):
        print(__Title__ + ":Start save settings")

        FreeCAD.ParamGet(self.userParams).SetString("Version",__Version__ + " (" + __Date__ + ")")

        FreeCAD.ParamGet(self.userParams).SetBool  ("switchResetToDefaults",    self.switchResetToDefaults)
        FreeCAD.ParamGet(self.userParams).SetBool  ("switchModeTextList",       self.switchModeTextList)
        FreeCAD.ParamGet(self.userParams).SetBool  ("switchFontComBox",         self.switchFontComBox)
        FreeCAD.ParamGet(self.userParams).SetBool  ("setSystemFonts",           self.setSystemFonts)
        FreeCAD.ParamGet(self.userParams).SetInt   ("setTextAlignement",        self.setTextAlignement)

        FreeCAD.ParamGet(self.userParams).SetString("text",                     self.TE_Text.toPlainText())
        FreeCAD.ParamGet(self.userParams).SetString("fontName",                 self.fontName)
        FreeCAD.ParamGet(self.userParams).SetInt   ("split",                    self.CB_Split.currentIndex())

        FreeCAD.ParamGet(self.userParams).SetBool  ("fixedAngle",               self.CB_Fixed_Angle.isChecked())

        FreeCAD.ParamGet(self.userParams).SetFloat ("radius",                   self.DS_Radius_Circle.value())
        FreeCAD.ParamGet(self.userParams).SetFloat ("beginAngle",               self.DS_Begin_Angle.value())
        FreeCAD.ParamGet(self.userParams).SetFloat ("endAngle",                 self.DS_End_Angle.value())
        FreeCAD.ParamGet(self.userParams).SetFloat ("characterSize",            self.DS_Size_Character.value())

        FreeCAD.ParamGet(self.userParams).SetBool  ("helixEnable",              self.CB_Helix.isChecked())
        FreeCAD.ParamGet(self.userParams).SetFloat ("helixBase",                self.DS_Helix_Base.value())
        FreeCAD.ParamGet(self.userParams).SetFloat ("helixEnd",                 self.DS_Helix_End.value())
        FreeCAD.ParamGet(self.userParams).SetFloat ("helixPitch",               self.DS_Helix_Pitch.value())
        FreeCAD.ParamGet(self.userParams).SetFloat ("numberCharPerTern",        self.DS_Helix_Char_Per_Turn.value())
        FreeCAD.ParamGet(self.userParams).SetFloat ("helixLoops",               self.DS_Helix_Loops.value())

        FreeCAD.ParamGet(self.userParams).SetBool  ("setExtrude",               self.CB_Extrude.isChecked())
        FreeCAD.ParamGet(self.userParams).SetFloat ("extrude",                  self.DS_Extrude.value())

        FreeCAD.ParamGet(self.userParams).SetBool  ("setPlacement",             self.CB_Placement.isChecked())
        FreeCAD.ParamGet(self.userParams).SetFloat ("PlacementX",               self.DS_PlacementX.value())
        FreeCAD.ParamGet(self.userParams).SetFloat ("PlacementY",               self.DS_PlacementY.value())
        FreeCAD.ParamGet(self.userParams).SetFloat ("PlacementZ",               self.DS_PlacementZ.value())

        FreeCAD.ParamGet(self.userParams).SetFloat ("inclinationX",             self.DS_InclinationX.value())
        FreeCAD.ParamGet(self.userParams).SetFloat ("inclinationY",             self.DS_InclinationY.value())
        FreeCAD.ParamGet(self.userParams).SetFloat ("inclinationZ",             self.DS_InclinationZ.value())

        FreeCAD.ParamGet(self.userParams).SetBool  ("support",                  self.CB_Support.isChecked())
        FreeCAD.ParamGet(self.userParams).SetFloat ("radiusSupport",            self.DS_Radius_Support.value())
        FreeCAD.ParamGet(self.userParams).SetInt   ("nombreFaces",              self.S_Number_Faces_Support.value())
        FreeCAD.ParamGet(self.userParams).SetFloat ("extrudeSupport",           self.DS_Extrude_Support.value())
        FreeCAD.ParamGet(self.userParams).SetFloat ("rotateSupport",            self.DS_Rotate_Support.value())

        FreeCAD.ParamGet(self.userParams).SetBool  ("points",                   self.CB_Points        .isChecked())
        FreeCAD.ParamGet(self.userParams).SetBool  ("circle",                   self.CB_Circle        .isChecked())
        FreeCAD.ParamGet(self.userParams).SetBool  ("boundBox",                 self.CB_BoundBox      .isChecked())
        FreeCAD.ParamGet(self.userParams).SetBool  ("progression",              self.CB_Progression   .isChecked())
                                                                                           
        FreeCAD.ParamGet(self.userParams).SetBool  ("solid",                    self.CB_Solid         .isChecked())
        FreeCAD.ParamGet(self.userParams).SetBool  ("liveUpdate",               self.CB_Live_Update   .isChecked())

        FreeCAD.ParamGet(self.userParams).SetBool  ("charAlignTL",              self.RB_Top_Left      .isChecked())
        FreeCAD.ParamGet(self.userParams).SetBool  ("charAlignTM",              self.RB_Top_Mid       .isChecked())
        FreeCAD.ParamGet(self.userParams).SetBool  ("charAlignTR",              self.RB_Top_Right     .isChecked())
        FreeCAD.ParamGet(self.userParams).SetBool  ("charAlignML",              self.RB_Mid_Left      .isChecked())
        FreeCAD.ParamGet(self.userParams).SetBool  ("charAlignMM",              self.RB_Mid_Mid       .isChecked())
        FreeCAD.ParamGet(self.userParams).SetBool  ("charAlignMR",              self.RB_Mid_Right     .isChecked())
        FreeCAD.ParamGet(self.userParams).SetBool  ("charAlignBL",              self.RB_Bot_Left      .isChecked())
        FreeCAD.ParamGet(self.userParams).SetBool  ("charAlignBM",              self.RB_Bot_Mid       .isChecked())
        FreeCAD.ParamGet(self.userParams).SetBool  ("charAlignBR",              self.RB_Bot_Right     .isChecked())

        FreeCAD.ParamGet(self.userParams).SetBool  ("extrudeAlignF",            self.RB_Extrude_Front .isChecked())
        FreeCAD.ParamGet(self.userParams).SetBool  ("extrudeAlignM",            self.RB_Extrude_Middle.isChecked())
        FreeCAD.ParamGet(self.userParams).SetBool  ("extrudeAlignB",            self.RB_Extrude_Back  .isChecked())

        print(__Title__ + ":Done save settings")

    def load_Settings(self):
        print(__Title__ + ":Start load settings")

        prefVersion = FreeCAD.ParamGet(self.userParams).GetString("Version",__Version__ + " (" + __Date__ + ")")

        if prefVersion == __Version__ + " (" + __Date__ + ")":
            ###### Read Configuration if version matches begin ####
            self.switchResetToDefaults            = FreeCAD.ParamGet(self.userParams).GetBool   ("switchResetToDefaults",   self.switchResetToDefaults)
            self.switchModeTextList               = FreeCAD.ParamGet(self.userParams).GetBool   ("switchModeTextList",      self.switchModeTextList)
            self.switchFontComBox                 = FreeCAD.ParamGet(self.userParams).GetBool   ("switchFontComBox",        self.switchFontComBox)
            self.setSystemFonts                   = FreeCAD.ParamGet(self.userParams).GetBool   ("setSystemFonts",          self.setSystemFonts)
            self.setTextAlignement                = FreeCAD.ParamGet(self.userParams).GetInt    ("setTextAlignement",       self.setTextAlignement)

            self.TE_Text         .setText(_fromUtf8(FreeCAD.ParamGet(self.userParams).GetString ("text",                    self.TE_Text.toPlainText())))
            self.fontName                         = FreeCAD.ParamGet(self.userParams).GetString ("fontName",                self.fontName)
            self.searchFont(self.fontDir,self.fontName)                                                                     
            self.CB_Split               .setCurrentIndex(FreeCAD.ParamGet(self.userParams).GetInt   ("split",               self.CB_Split.currentIndex()))

            self.CB_Fixed_Angle         .setChecked(FreeCAD.ParamGet(self.userParams).GetBool   ("fixedAngle",              self.CB_Fixed_Angle.isChecked()))

            self.DS_Radius_Circle       .setValue  (FreeCAD.ParamGet(self.userParams).GetFloat  ("radius",                  self.DS_Radius_Circle.value()))
            self.DS_Begin_Angle         .setValue  (FreeCAD.ParamGet(self.userParams).GetFloat  ("beginAngle",              self.DS_Begin_Angle.value()))
            self.DS_End_Angle           .setValue  (FreeCAD.ParamGet(self.userParams).GetFloat  ("endAngle",                self.DS_End_Angle.value()))
            self.DS_Size_Character      .setValue  (FreeCAD.ParamGet(self.userParams).GetFloat  ("characterSize",           self.DS_Size_Character.value()))

            self.CB_Helix               .setChecked(FreeCAD.ParamGet(self.userParams).GetBool   ("helixEnable",             self.CB_Helix.isChecked()))
            self.DS_Helix_Base          .setValue  (FreeCAD.ParamGet(self.userParams).GetFloat  ("helixBase",               self.DS_Helix_Base.value()))
            self.DS_Helix_End           .setValue  (FreeCAD.ParamGet(self.userParams).GetFloat  ("helixEnd",                self.DS_Helix_End.value()))
            self.DS_Helix_Pitch         .setValue  (FreeCAD.ParamGet(self.userParams).GetFloat  ("helixPitch",              self.DS_Helix_Pitch.value()))
            self.DS_Helix_Char_Per_Turn .setValue  (FreeCAD.ParamGet(self.userParams).GetFloat  ("numberCharPerTern",       self.DS_Helix_Char_Per_Turn.value()))
            self.DS_Helix_Loops         .setValue  (FreeCAD.ParamGet(self.userParams).GetFloat  ("helixLoops",              self.DS_Helix_Loops.value()))

            extrude                               = FreeCAD.ParamGet(self.userParams).GetBool   ("setExtrude",              self.CB_Extrude.isChecked())
            self.CB_Extrude.setChecked(extrude)
            self.DS_Extrude             .setValue  (FreeCAD.ParamGet(self.userParams).GetFloat  ("extrude",                 self.DS_Extrude.value()))
            self.DS_Extrude.setEnabled(extrude)
            self.RB_Extrude_Front.setEnabled(extrude)
            self.RB_Extrude_Middle.setEnabled(extrude)
            self.RB_Extrude_Back.setEnabled(extrude)
            self.GB_Extrude_Align.setEnabled(extrude)
            self.CB_Solid.setEnabled(extrude)

            placement                             = FreeCAD.ParamGet(self.userParams).GetBool   ("setPlacement",            self.CB_Placement.isChecked())
            self.CB_Placement.setChecked(placement)
            self.DS_PlacementX          .setValue  (FreeCAD.ParamGet(self.userParams).GetFloat  ("PlacementX",              self.DS_PlacementX.value()))
            self.DS_PlacementY          .setValue  (FreeCAD.ParamGet(self.userParams).GetFloat  ("PlacementY",              self.DS_PlacementY.value()))
            self.DS_PlacementZ          .setValue  (FreeCAD.ParamGet(self.userParams).GetFloat  ("PlacementZ",              self.DS_PlacementZ.value()))
            self.DS_PlacementX.setEnabled(placement)                                                                    
            self.DS_PlacementY.setEnabled(placement)                                                                    
            self.DS_PlacementZ.setEnabled(placement)                                                                    

            self.DS_InclinationX        .setValue  (FreeCAD.ParamGet(self.userParams).GetFloat  ("inclinationX",            self.DS_InclinationX.value()))
            self.DS_InclinationY        .setValue  (FreeCAD.ParamGet(self.userParams).GetFloat  ("inclinationY",            self.DS_InclinationY.value()))
            self.DS_InclinationZ        .setValue  (FreeCAD.ParamGet(self.userParams).GetFloat  ("inclinationZ",            self.DS_InclinationZ.value()))

            support                               = FreeCAD.ParamGet(self.userParams).GetBool   ("support",                 self.CB_Support.isChecked())
            self.CB_Support.setChecked(support)
            self.DS_Radius_Support      .setValue  (FreeCAD.ParamGet(self.userParams).GetFloat  ("radiusSupport",           self.DS_Radius_Support.value()))
            self.S_Number_Faces_Support .setValue  (FreeCAD.ParamGet(self.userParams).GetInt    ("nombreFaces",             self.S_Number_Faces_Support.value()))
            self.DS_Extrude_Support     .setValue  (FreeCAD.ParamGet(self.userParams).GetFloat  ("extrudeSupport",          self.DS_Extrude_Support.value()))
            self.DS_Rotate_Support      .setValue  (FreeCAD.ParamGet(self.userParams).GetFloat  ("rotateSupport",           self.DS_Rotate_Support.value()))
            self.DS_Radius_Support.setEnabled(support)
            self.S_Number_Faces_Support.setEnabled(support)
            self.DS_Extrude_Support.setEnabled(support)
            self.DS_Rotate_Support.setEnabled(support)

            self.CB_Points              .setChecked(FreeCAD.ParamGet(self.userParams).GetBool   ("points",                  self.CB_Points          .isChecked()))
            self.CB_Circle              .setChecked(FreeCAD.ParamGet(self.userParams).GetBool   ("circle",                  self.CB_Circle          .isChecked()))
            self.CB_BoundBox            .setChecked(FreeCAD.ParamGet(self.userParams).GetBool   ("boundBox",                self.CB_BoundBox        .isChecked()))
            self.CB_Progression         .setChecked(FreeCAD.ParamGet(self.userParams).GetBool   ("progression",             self.CB_Progression     .isChecked()))

            self.CB_Solid               .setChecked(FreeCAD.ParamGet(self.userParams).GetBool   ("solid",                   self.CB_Solid           .isChecked()))
            self.CB_Live_Update         .setChecked(FreeCAD.ParamGet(self.userParams).GetBool   ("liveUpdate",              self.CB_Live_Update     .isChecked()))

            self.RB_Top_Left            .setChecked(FreeCAD.ParamGet(self.userParams).GetBool   ("charAlignTL",             self.RB_Top_Left        .isChecked()))
            self.RB_Top_Mid             .setChecked(FreeCAD.ParamGet(self.userParams).GetBool   ("charAlignTM",             self.RB_Top_Mid         .isChecked()))
            self.RB_Top_Right           .setChecked(FreeCAD.ParamGet(self.userParams).GetBool   ("charAlignTR",             self.RB_Top_Right       .isChecked()))
            self.RB_Mid_Left            .setChecked(FreeCAD.ParamGet(self.userParams).GetBool   ("charAlignML",             self.RB_Mid_Left        .isChecked()))
            self.RB_Mid_Mid             .setChecked(FreeCAD.ParamGet(self.userParams).GetBool   ("charAlignMM",             self.RB_Mid_Mid         .isChecked()))
            self.RB_Mid_Right           .setChecked(FreeCAD.ParamGet(self.userParams).GetBool   ("charAlignMR",             self.RB_Mid_Right       .isChecked()))
            self.RB_Bot_Left            .setChecked(FreeCAD.ParamGet(self.userParams).GetBool   ("charAlignBL",             self.RB_Bot_Left        .isChecked()))
            self.RB_Bot_Mid             .setChecked(FreeCAD.ParamGet(self.userParams).GetBool   ("charAlignBM",             self.RB_Bot_Mid         .isChecked()))
            self.RB_Bot_Right           .setChecked(FreeCAD.ParamGet(self.userParams).GetBool   ("charAlignBR",             self.RB_Bot_Right       .isChecked()))

            self.RB_Extrude_Front       .setChecked(FreeCAD.ParamGet(self.userParams).GetBool   ("extrudeAlignF",           self.RB_Extrude_Front   .isChecked()))
            self.RB_Extrude_Middle      .setChecked(FreeCAD.ParamGet(self.userParams).GetBool   ("extrudeAlignM",           self.RB_Extrude_Middle  .isChecked()))
            self.RB_Extrude_Back        .setChecked(FreeCAD.ParamGet(self.userParams).GetBool   ("extrudeAlignB",           self.RB_Extrude_Back    .isChecked()))

        print(__Title__ + ":Done load settings")

###### Read Configuration end   ####
##################################################################################################
class SelObserver:
    def addSelection(self, document, object, element, position):  # Selection
        global ui
        #print("addSelection",position)

        try:
            selectedEdge = FreeCADGui.Selection.getSelectionEx()[0].SubObjects[0]  # select one subElement
            if (hasattr(selectedEdge,'Surface')) or (hasattr(selectedEdge,'Point')):
                if (hasattr(selectedEdge,'Point')):
                    ui.PlacementX = position[0]
                    ui.PlacementY = position[1]
                    ui.PlacementZ = position[2]
                    ui.CB_Placement.setChecked(True)
                    ui.on_CB_Placement(True)
                    ui.DS_PlacementX.setValue(ui.PlacementX)
                    ui.DS_PlacementY.setValue(ui.PlacementY)
                    ui.DS_PlacementZ.setValue(ui.PlacementZ)
            else:
                ui.DS_Radius_Circle.setEnabled(False)
                ui.DS_Radius_Circle.setStyleSheet("background-color: #F8E0E0;")
                ui.DS_Begin_Angle.setEnabled(False)
                ui.DS_Begin_Angle.setStyleSheet("background-color: #F8E0E0;")
                ui.DS_End_Angle.setEnabled(False)
                ui.DS_End_Angle.setStyleSheet("background-color: #F8E0E0;")
                ui.CB_Circle.setChecked(False)
                ui.CB_Circle.setEnabled(False)
                ui.CB_Circle.setStyleSheet("background-color: #F8E0E0;")
        except Exception:
            pass

#    def setPreselection(self,doc,obj,sub):             # preselection
#        print("setPreselection")
#
#    def removeSelection(self,doc,obj,sub):             # Effacer l'objet selectionne
#        print("removeSelection")
#
#    def setSelection(self,doc):                        # Selection dans ComboView
#        print("SelObserver quit macro")

    def clearSelection(self,doc):                      # Si clic sur l'ecran, effacer la selection
        #print("clearSelection")

        #ui.CB_Placement.setChecked(False)
        #ui.on_CB_Placement(False)
        ui.DS_Radius_Circle.setEnabled(True)
        ui.DS_Radius_Circle.setStyleSheet("Base")
        ui.DS_Begin_Angle.setEnabled(True)
        ui.DS_Begin_Angle.setStyleSheet("Base")
        ui.DS_End_Angle.setEnabled(True)
        ui.DS_End_Angle.setStyleSheet("Base")
        ui.CB_Circle.setEnabled(True)
        ui.CB_Circle.setStyleSheet("Base")

s=SelObserver()
FreeCADGui.Selection.addObserver(s)                    # installe la fonction en mode resident
###################################################################################################

# deselecter tous les objets
try:
    for obj in FreeCAD.ActiveDocument.Objects:         # deslectionne tout
        FreeCADGui.Selection.removeSelection(obj)
except Exception:
    None

MainWindow = QtWidgets.QMainWindow()
ui = Ui_MainWindow()
ui.setupUi(MainWindow)
MainWindow.show()
